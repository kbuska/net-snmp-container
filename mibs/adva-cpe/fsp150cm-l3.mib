F3-L3-MIB DEFINITIONS ::= BEGIN

IMPORTS
    MODULE-IDENTITY, OBJECT-TYPE, Integer32, Unsigned32, IpAddress, Counter64
             FROM SNMPv2-SMI
    MODULE-COMPLIANCE, OBJECT-GROUP
             FROM SNMPv2-CONF
    DateAndTime, DisplayString, TruthValue, RowStatus, StorageType, 
    MacAddress, VariablePointer, TEXTUAL-CONVENTION
             FROM SNMPv2-TC
    Ipv6Address
             FROM IPV6-TC
    InterfaceIndex, ifIndex
             FROM IF-MIB
    PhysicalIndex
             FROM ENTITY-MIB
    fsp150cm
             FROM  ADVA-MIB 
    AdminState, OperationalState, SecondaryState, VlanId, VlanPriority,
    F3DisplayString, IpVersion, TrafficDirection, 
    CmPmIntervalType, CmPmBinAction, PerfCounter64, FlowSecState
             FROM  CM-COMMON-MIB
    CmDhcpRole, DHCPHostNameType, DHCPCIDType, IpEntryType, IpMode
             FROM  CM-IP-MIB
    neIndex, shelfIndex, slotIndex
             FROM CM-ENTITY-MIB
    PolicerAlgorithmType, PolicerColorMode, AclNoMatchDispositionType,
    ShapingType
             FROM CM-FACILITY-MIB;

f3L3MIB MODULE-IDENTITY
    LAST-UPDATED    "202108150000Z"
    ORGANIZATION    "ADVA Optical Networking SE"
    CONTACT-INFO
        "Web URL: http://adva.com/
        E-mail:  support@adva.com
        Postal:  ADVA Optical Networking SE
             Campus Martinsried
             Fraunhoferstrasse 9a
             82152 Martinsried/Munich
             Germany
        Phone: +49 089 89 06 65 0
        Fax:  +49 089 89 06 65 199 "
    DESCRIPTION
            "This module defines the L3 MIB definitions used by 
             the F3 (FSP150CM/CC) product lines.
             Copyright (C) ADVA."
    REVISION        "202108150000Z"
    DESCRIPTION
       "
        Notes from release 202209100000Z
        (1) Added new enum:
                DhcpMatchType,
                DhcpIpAddrBindType,
                DhcpIPv4AddrPoolActionType
        (2) Added new table:
                f3L3DhcpClassTable,
                f3L3DhcpRuleTable,
                f3L3DhcpIPv4AddrPoolTable,
                f3L3DhcpExcludedIPv4AddrListTable,
                f3L3DhcpStaticBindingIPv4AddrTable,
                f3L3DhcpActiveLeaseIPv4AddrTable
        (3) Added new group:
                f3L3DhcpGroup
		
        Notes from release 202108150000Z
        (1) Added new table:
            - f3L3TrafficOspfAreaRouteSummaryTable:
        (2) Added the following objects to f3DhcpRelayAgentTable:
            - f3DhcpRelayAgentServerIpAddressList
        (3) Added the following objects to f3DhcpV6VelayAgentTable:
            - f3DhcpV6RelayAgentServerIpAddressList
        
        Notes from release 201908010000Z
        (1) Added new objects to f3L3TrafficIPInterfaceTable:
             f3L3TrafficIPIfMtu

        Notes from release 201810250000Z
        (1) Added new objects to cmL3FlowPointTable:
             cmL3FlowPointEgressShapingType

        Notes from release 201810240000Z
        (1) Added new objects to cmL3FlowPointTable:
             cmL3FlowPointWfqSegmentationCOS
             cmL3FlowPointWfqGroupCOS
             cmL3FlowPointWfqGroupEirLo
             cmL3FlowPointWfqGroupEirHi
        (2) Added new object to cmL3QosShaperTable:
             cmL3QosShaperWfqWeight

      Notes from release 201809060000Z
        (1) Added new table:
            f3L3TrafficIpv4AllRouteTable
        (2) Deprecated table:
            f3L3TrafficIpv4RouteTable
        
        Notes from release 201808010000Z
        (1) Added new attribute:
            f3L3TrafficBgpPeerLocalPreference
            f3L3TrafficBgpPeerRouteReflectorClient
            f3L3TrafficBgpPeerRouteReflectorClusterId

        Notes from release 201807130000Z
        (1) Added new attribute:
            f3VrfOspfRouterVersion

         Notes from release 201807130000Z
        (1) Depreceted attribute:
            f3L3TrafficOspfNeighborInterface
        (2) Added new attribute:
            f3L3TrafficOspfNeighborLocalInterfaceName

        Notes from release 201807120000Z
        (1) Depreceted attributes:
            f3L3TrafficBgpRouterConnectedRoutesRedistControl
            f3L3TrafficBgpRouterOspfRoutesRedistControl
            f3L3TrafficBgpRouterStaticRoutesRedistControl
            f3L3TrafficBgpRouterDhcpRoutesRedistControl 
        
        Notes from release 201806260000Z
        (1) Added new table:
            f3L3TrafficBgpPeerAddressFamilyTable

        Notes from release 201806200000Z
          (1) Renamed OspfRole to TrafficOspfRole.
          (2) Renamed OspfAreaType to TrafficOspfAreaType.

         Notes from release 201802020000Z
           (1) Added new tables:
               f3L3TrafficBgpRouterTable,
               f3L3TrafficBgpRouteTable,
               f3L3TrafficBgpPeerTable,
               f3VrfOspfRouterTable,
               f3L3TrafficOspfAreaTable,
               f3L3TrafficOspfAreaIfMemberTable,
               f3VrfLoopbackInterfaceTable,
               f3L3TrafficOspfAsLsDbTable,
               f3L3TrafficOspfLsDbTable,
               f3L3TrafficOspfNeighborTable,
               f3L3TrafficIPInterfaceOspfTable,
               f3L3TrafficIPv6InterfaceTable,
               f3L3TrafficIPv6AddressTable,
               f3L3TrafficIPv6PrefixTable,
               f3L3TrafficIPv6NdpTable,
               f3L3TrafficIpv6RouteTable,
               f3DhcpV6RelayAgentTable,
               f3DhcpV6RelayAgentClientTrafficIpIfMemberTable
           (2) Deprecated f3VrfAction, added f3VrfActionX
           (3) Deprecated f3L3TrafficIpv4RouteStatus, 
               added f3L3TrafficIpv4RouteStatusX
           (4) Deprecated f3L3TrafficIPIfAction,
               added f3L3TrafficIPIfActionX

           Notes from release 201712140000Z
            1) added cmL3FlowPointThresholdCrossingAlert, cmL3QosPolicerThresholdCrossingAlert, 
               cmL3QosShaperThresholdCrossingAlert
            2) changed the range of f3L3TrafficIpInterfaceHistoryIndex from 1..4 to 1..65535
            3) changed the range of f3L3AclRuleHistoryIndex from 1..4 to 1..65535
            4) changed the range of cmL3FlowPointHistoryIndex from 1..4 to 1..65535

          Notes from release 201711300000Z
            a) added cmL3FlowPointAclNoMatchDisposition to CML3FlowPointEntry

          Notes from release 201711270000Z
            a) added cmL3FlowPointStatsAclDropNoMatch to CML3FlowPointStatsEntry
            b) added cmL3FlowPointHistoryAclDropNoMatch to CML3FlowPointHistoryEntry

          Notes from release 201711130000Z
            a) added f3VrfActionIfName to f3VrfTable
            b) moved the action flushArpCache from TrafficIpInterfaceActionType to VrfActionType

          Notes from release 201711050000Z
            a) marked f3VrfAccIsolationControlEnabled obsolete
            b) added VrfActionType and deprecated VrfAction
            c) deprecaed f3VrfAction and added f3VrfActionX
            d) deprecated TrafficIpRouteStatus and added TrafficIpRouteStatusType
            e) deprecated AffectiveArpActionType and added TrafficIpInterfaceActionType 
            f) mark f3L3TrafficIpv4RouteFlags obsolete
            g) deprecated f3L3TrafficIpv4RouteStatus and added f3L3TrafficIpv4RouteStatusX
            h) deprecated f3L3TrafficIPIfAction and added f3L3TrafficIPIfActionX

          Notes from release 201709200000Z
            a) change f3L3TrafficIPIfDhcpEnabled to read-write

          Notes from release 201709150000Z
            a) moved PointPolicingEnabled attribute from cmL3FlowPointTable to cmL3QosPolicerTable

          Notes from release 201708150000Z
            a) added the following tables to suport xgpro NIDs
              cmL3FlowPointTable
              cmL3QosPolicerTable
              cmL3QosShaperTable
              cmL3FlowPointStatsTable
              cmL3FlowPointHistoryTable
              cmL3FlowPointThresholdTable
              cmL3QosPolicerStatsTable
              cmL3QosPolicerHistoryTable
              cmL3QosPolicerThresholdTable
              cmL3QosShaperStatsTable
              cmL3QosShaperHistoryTable
              cmL3QosShaperThresholdTable

           Notes from release 201703220000Z
              (1) New f3L3AclRuleTable column:
                  - f3L3AclRuleActive

          Notes from release 201409120000Z"
    ::= {fsp150cm 37}    

-- 
-- OID definitions
-- 
f3L3Objects        OBJECT IDENTIFIER ::= {f3L3MIB 1}
f3L3Performance    OBJECT IDENTIFIER ::= {f3L3MIB 2}
f3L3Notifications  OBJECT IDENTIFIER ::= {f3L3MIB 3}
f3L3Conformance    OBJECT IDENTIFIER ::= {f3L3MIB 4}
cmL3Notifications  OBJECT IDENTIFIER ::= {f3L3MIB 5}

--
-- Textual Conventions
--
BgpGracefulRestartControlType ::= TEXTUAL-CONVENTION
    STATUS       current
    DESCRIPTION
        "."
    SYNTAX       INTEGER {
                   notApplicable (0),
                   enable (1),
                   disable (2),
                   helperOnly (3)
                 }

EcmpDistributionType ::= TEXTUAL-CONVENTION
    STATUS       current
    DESCRIPTION
        "."
    SYNTAX       INTEGER {
                   notApplicable (0),
                   l3 (1),
                   l4 (2)
                 }
                 
BgpUpdateSourceType ::= TEXTUAL-CONVENTION
    STATUS       current
    DESCRIPTION
        "The type to update source IP."
    SYNTAX       INTEGER {
                   notApplicable (0),
                   none (1),
                   ipv4Address (2),
                   ipv6Address (3),
                   interfaceName (4)
                 }

BgpRouteFilterDirection ::= TEXTUAL-CONVENTION
    STATUS       current
    DESCRIPTION
        "Config parameters related to inbound or outbound route filter."
    SYNTAX       INTEGER {
                   notApplicable (0),
                   in (1),
                   out (2)
                 }

IpPrefixDispositionType ::= TEXTUAL-CONVENTION
    STATUS       current
    DESCRIPTION
        "IP Prefix Disposition Type."
    SYNTAX       INTEGER {
                   notApplicable (0),
                   permit (1),
                   deny (2)
                 }

BgpRouterActionType ::= TEXTUAL-CONVENTION
    STATUS       current
    DESCRIPTION
        "Describes the action on BGP Router."
    SYNTAX       INTEGER {
                   notApplicable (0),
                   optimizeBgpRouteRetrieve (1),
                   optimizeBgpInRouteRetrieve (2)
                 }
                 
OspfRouterActionType ::= TEXTUAL-CONVENTION
    STATUS       current
    DESCRIPTION
        "Describes the action on OSPF Router."
    SYNTAX       INTEGER {
                   notApplicable (0),
                   optimizeOspfAsLsDbRetrieve (1),
                   optimizeOspfLsDbRetrieve (2),
                   optimizeOspfNeighborRetrieve (3),
                   optimizeOspfLinkLsDbRetrieve (4)
                 }
                 
Ipv6AddressAssignMode ::= TEXTUAL-CONVENTION
    STATUS       current
    DESCRIPTION
        "Describes IPv6 address assignment mode."
    SYNTAX       INTEGER {
                   notApplicable (0),
                   manual (1),
                   automatic (2),
                   external (3)
                 }
                 
TrafficIpRouteOriginType ::= TEXTUAL-CONVENTION
    STATUS       current
    DESCRIPTION
        "The origin type of IP Route.
         bgp (1)       --  From BGP.
         ospf (2)      --  From OSPF.
         connected (3) --  Connected Route.
         static (4)    --  Configured.
         dhcp (5)       --  From DHCP Relay.
         slaac (6)      --  From SLACC.
         dhcp-relay (7) --  From DHCP.
         isis (8)       --  From ISIS.
         ti-lfa (9)     --  From TI-LFA.
"
    SYNTAX       INTEGER {
                   notApplicable (0),
                   bgp (1),
                   ospf (2),
                   connected (3),
                   static (4),
                   dhcp (5),
                   slaac (6),
                   dhcp-relay (7),
                   isis (8),
                   ti-lfa (9)
                 }
                 
NdpNeighborReachabilityState ::= TEXTUAL-CONVENTION
    STATUS       current
    DESCRIPTION
        "Reachability state of NDP entry."
    SYNTAX       INTEGER {
                   notApplicable (0),
                   incomplete (1),
                   reachable (2),
                   stale (3),
                   delay (4),
                   probe (5)
                 }
                 
NdpRaDefaultRouterPreference ::= TEXTUAL-CONVENTION
    STATUS       current
    DESCRIPTION
        "Describes Router preference."
    SYNTAX       INTEGER {
                   notApplicable (0),
                   none (1),
                   high (2),
                   medium (3),
                   low (4)
                 }
                 
Ipv6LinkLocalAddressMode ::= TEXTUAL-CONVENTION
    STATUS       current
    DESCRIPTION
        "IPv6 address shall be first 64 bits as configured in IPv6 unicast 
         address auto generation prefix followed by Interface ID."
    SYNTAX       INTEGER {
                   notApplicable (0),
                   automatic (1),
                   manual (2)
                 }
                 
IpInterfaceType ::= TEXTUAL-CONVENTION
    STATUS       current
    DESCRIPTION
        "Describes IPv6 interface type."
    SYNTAX       INTEGER {
                   notApplicable (0),
                   host (1),
                   router (2)
                 }

OspfAuthType ::= TEXTUAL-CONVENTION
    STATUS       current
    DESCRIPTION
        "This attribute is used to specify authentication type. 
         Simple: 64-bits clear password inserted into OSPF packets header.
         None: No authentication is used.
         Cryptographic: a shared secret which enables the generation/verification 
         of message digests which are appended to the OSPF protocol packets.
         none (1)          --  No authentication.
         simple (2)        --  64-bits clear password inserted into OSPF packets header.
         cryptoGraphic (3) --  A shared secret which enables the generation/verification of 
                               message digests which are appended to the OSPF protocol packets.
                               System level authentication key is used."
    SYNTAX       INTEGER {
                   notApplicable (0),
                   none (1),
                   simple (2),
                   cryptoGraphic (3)
                 }
                 
OspfInterfaceState ::= TEXTUAL-CONVENTION
    STATUS       current
    DESCRIPTION
        "The OSPF state of interface.
         down (1)          -- In this state, the lower-level protocols 
                              have indicated that the interface is unusable.
         loopback (2)      -- The interface is looped back and unavailable 
                              for regular data traffic.
         waiting (3),      -- In this state, the router is trying to determine 
                              the identity of the (Backup) Designated Router for the network. 
                              To do this, the router monitors the Hello Packets it receives. 
                              The router is not allowed to elect a Backup Designated Router nor 
                              a Designated Router until it transitions out of Waiting state. 
                              This prevents unnecessary changes of (Backup) Designated Router.
         pointToPoint (4), -- In this state, the interface is operational, and connects 
                              either to a physical point-to-point network or to a virtual link. 
                              Upon entering this state, the router attempts to form an 
                              adjacency with the neighboring router. Hello Packets are sent 
                              to the neighbor every HelloInterval seconds.
         drOther (5),      -- The interface is to a broadcast or NBMA network 
                              on which another router has been selected to be the Designated Router. 
                              In this state, the router itself has not been selected Backup 
                              Designated Router either. The router forms adjacencies to both the 
                              Designated Router and the Backup Designated Router (if they exist).
         dr (6),           -- In this state, this router itself is the Designated Router 
                              on the attached network.
         backup (7)        -- In this state, the router itself is the Backup Designated 
                              Router on the attached network."
    SYNTAX       INTEGER {
                   notApplicable (0),
                   down (1),
                   loopback (2),
                   waiting (3),
                   pointToPoint (4),
                   drOther (5),
                   dr (6),
                   backup (7)
                 }

OspfIfType ::= TEXTUAL-CONVENTION
    STATUS       current
    DESCRIPTION
        "The network type connected by interface.
         broadcast (1)    --  Broadcast.
         pointToPoint (2) --  Point to Point."
    SYNTAX       INTEGER {
                   notApplicable (0),
                   broadcast (1),
                   pointToPoint (2),
                   loopback (3)
                 }
                 
TrafficOspfRole ::= TEXTUAL-CONVENTION
    STATUS       current
    DESCRIPTION
        "The role of router.
         dr (1)      --  Designated Router.
         bdr (2)     --  Backup DR.
         drother (3) --  DR Other.
         pointToPoint(4) -- Point to point"
    SYNTAX       INTEGER {
                   notApplicable (0),
                   dr (1),
                   bdr (2),
                   drother (3),
                   pointToPoint (4)
                 }

OspfAdjacencyState ::= TEXTUAL-CONVENTION
    STATUS       current
    DESCRIPTION
        "OSPF Interface Adjacency State.
         down (1)     --  Neighbor down state.
         attempt (2)  --  Neighbor attempt state.
         init (3)     --  Neighbor init state.
         twoWay (4)   --  Neighbor 2-Way state.
         exStart (5)  --  Neighbor exchange start state.
         exchange (6) --  Neighbor exchange state.
         loading (7)  --  Neighbor loading state.
         full (8)     --  Neighbor full state."
    SYNTAX       INTEGER {
                   notApplicable (0),
                   down (1),
                   attempt (2),
                   init (3),
                   twoWay (4),
                   exStart (5),
                   exchange (6),
                   loading (7),
                   full (8)
                 }

OspfAsLsaType ::= TEXTUAL-CONVENTION
    STATUS       current
    DESCRIPTION
        "Type of LSA from external AS.
         asExternal (1)  --  Autonomous system external LSA.
         asOpaque (2)    --  OSPF AS (Autonomous System) Scope Opaque LSA."
    SYNTAX       INTEGER {
                   notApplicable (0),
                   asExternal (1),
                   asOpaque (2)
                 }

OspfLsaType ::= TEXTUAL-CONVENTION
    STATUS       current
    DESCRIPTION
        "Type of LSA from external AS.
         router (1)     --  Router LSA: The Router LSA is generated by each 
                            router for each area it is located. In the link-state ID 
                            you will find the originating router's ID.
         network (2)    --  Network LSA: Network LSAs are generated by the DR. 
                            The link-state ID will be the router ID of the DR.
         summary (3)    --  Summary LSA: The summary LSA is created by the 
                            ABR and flooded into other areas.
         asExternal (4) --  External LSA: Also known as autonomous system external LSA, 
                            the external LSAs are generated by the ASBR.
         areaOpaque (5) --  Packets are used to flood OSPF information through other area routers 
                            even if these routers do not process this information in order to extend 
                            OSPF functionality, this LSA is used for traffic engineering to advertise 
                            MPLS and other protocols."
    SYNTAX       INTEGER {
                   notApplicable (0),
                   router (1),
                   network (2),
                   summary (3),
                   asExternal (4),
                   areaOpaque (5),
                   summaryNet (6),
                   summaryAsbr (7),
                   multicast (8),
                   nssaExternal (9),
                   interAreaPrefix (10),
                   interAreaRouter (11),
                   link (12),
                   intraAreaPrefix (13)
                 }

RoutesMetricType ::= TEXTUAL-CONVENTION
    STATUS       current
    DESCRIPTION
        "Metric Type for routes exported from external autonomous system.
         e1 (1) --  Type 1 external metrics are equivalent to the link-state metric, 
                    where the cost is equal to the sum of the internal costs plus the external 
                    cost. This means that Type 1 external metrics include the external cost 
                    to the destination as well as the cost (metric) to reach the AS boundary router.
         e2 (2) --  Type 2 external metrics are greater than the cost of any path internal 
                    to the AS. Type 2 external metrics use only the external cost to the destination 
                    and ignore the cost (metric) to reach the AS boundary router."
    SYNTAX       INTEGER {
                   notApplicable (0),
                   e1 (1),
                   e2 (2)
                 }

TrafficOspfAreaType ::= TEXTUAL-CONVENTION
    STATUS       current
    DESCRIPTION
        "Area Type."
    SYNTAX       INTEGER {
                   notApplicable (0),
                   stub (1),
                   normal (2)
                 }

BgpSessionStateType ::= TEXTUAL-CONVENTION
    STATUS       current
    DESCRIPTION
        "Operational state of the BGP peer.
         idle (1)        --  Neighbor is down, and in the Idle state of the FSM.
         connect (2)     --  Neighbor is down, and the session is waiting for
                             the underlying transport session to be established.
         active (3)      --  Neighbor is down, and the local system is awaiting
                             a conncetion from the remote peer.
         openSent (4)    --  Neighbor is in the process of being established.
                             The local system has sent an OPEN message.
         openConfirm (5) --  Neighbor is in the process of being established.
                             The local system is awaiting a NOTIFICATION or
                             KEEPALIVE message.
         established (6) --  Neighbor is up - the BGP session with the peer is
                             established."
    SYNTAX       INTEGER {
                   notApplicable (0),
                   idle (1),
                   connect (2),
                   active (3),
                   openSent (4),
                   openConfirm (5),
                   established (6)
                 }

BgpNextHopUpdateType ::= TEXTUAL-CONVENTION
    STATUS       current
    DESCRIPTION
        "."
    SYNTAX       INTEGER {
                   notApplicable (0),
                   default (1),
                   self (2),
                   ipv4 (3),
                   ipv6 (4)
                 }

BgpPeerAddressFamilyNameType ::= TEXTUAL-CONVENTION
    STATUS       current
    DESCRIPTION
        "."
    SYNTAX       INTEGER {
                   notApplicable (0),
                   ipv4-unicast (1),
                   ipv6-unicast (2)
                 }

OspfVersion ::= TEXTUAL-CONVENTION
    STATUS       current
    DESCRIPTION
        "Describes version of a Ospf Router."
    SYNTAX       INTEGER {
                   notApplicable (0),
                   ospfv2 (1),
                   ospfv3 (2)
                 }
--
-- DEPRECATED
--
VrfAction ::= TEXTUAL-CONVENTION
    STATUS       deprecated
    DESCRIPTION
        "Describes the action on Vrf."
    SYNTAX       INTEGER {
                   notApplicable (0),
                   ping (1),
                   fluchARPCache(2), 
                   traceRoute(3),
                   retrieveEffectiveRoutes(4)
                 }
--
-- replaces VrfAction
--
VrfActionType ::= TEXTUAL-CONVENTION
    STATUS       current
    DESCRIPTION
        "Describes the action on Vrf."
    SYNTAX       INTEGER {
                   notApplicable (0),
                   ping (1),
                   traceRoute(2),
                   optimizeRouteRetrieve(3),
                   flushArpCache (4),
                   pingV6(5),
                   traceRouteV6(6),
                   optimizeIpv6RouteRetrieve(7),
                   flushNDP (8),
                   optimizeBfdSessionRetrieve(9)
                 }

IfIpAddressSourceType ::= TEXTUAL-CONVENTION
    STATUS       current
    DESCRIPTION
        "Describes the Ip Interface adress source type."
    SYNTAX       INTEGER {
                   dhcp (1),
                   static(2)
                 }

DhcpRelayInterfaceSide ::= TEXTUAL-CONVENTION
    STATUS       current
    DESCRIPTION
        "Describes the DHCP relay interface side."
    SYNTAX       INTEGER {
                   client (1),
                   server(2)
                 }

L3AclRuleOperation ::= TEXTUAL-CONVENTION
    STATUS       current
    DESCRIPTION
        "Describes the acl rule operation."
    SYNTAX       INTEGER {
                   notApplicable (0),
                   accept (1),
                   deny (2)
                 }

AclRuleL2Side ::= TEXTUAL-CONVENTION
    STATUS       current
    DESCRIPTION
        "Describes the acl rule l2 side."
    SYNTAX       INTEGER {
                   access(1),
                   network(2)
                 }
--
-- DEPRECATED
--
TrafficIpRouteStatus ::= TEXTUAL-CONVENTION
    STATUS       deprecated
    DESCRIPTION
        "Describes the traffci ipv4 route status."
    SYNTAX       INTEGER {
                   active(1),
                   nexthopUnresovled(2),
                   interfaceOutage(3),
                   noResources(4),
                   standby(5),
                   bfdSessDown(6)
                 }


RouteFlags ::= TEXTUAL-CONVENTION
    STATUS       current
    DESCRIPTION
        "Describes the traffci ipv4 route flags."
    SYNTAX       BITS {
                   dDynamic(0),
                   gUseGW(1),
                   hFullMask(2),
                   mModifiedByIcmp(3),
                   oOutage(4),
                   uNormal(5)
                 }

--
-- replaces TrafficIpRouteStatus
--
TrafficIpRouteStatusType ::= TEXTUAL-CONVENTION
    STATUS       current
    DESCRIPTION
        "Describes the traffci ipv4 route status."
    SYNTAX       INTEGER {
                   active(1),
                   nexthopUnresolved(2),
                   interfaceOutage(3),
                   noResources(4),
                   standby(5),
                   bfdSessDown(6)
                 }
--
-- DEPRECATED
--
AffectiveArpActionType ::= TEXTUAL-CONVENTION
    STATUS       deprecated
    DESCRIPTION
        "Describes the retrieve effective arp action."
    SYNTAX       INTEGER {
                   notApplicable (0),
                   retrieveAffectiveArp (1)
                 }

--
-- replaces AffectiveArpActionType
--
TrafficIpInterfaceActionType ::= TEXTUAL-CONVENTION
    STATUS       current
    DESCRIPTION
        "Describes interface action."
    SYNTAX       INTEGER {
                   notApplicable (0),
                   optimizeArpRetrieve (1),
                   optimizeNdpRetrieve (2),
                   optimizeIPv6AddressEntryRetrieve (3)
                 }

TrafficIpv6InterfaceActionType ::= TEXTUAL-CONVENTION
    STATUS       current
    DESCRIPTION
        "Describes interface action."
    SYNTAX       INTEGER {
                   notApplicable (0),
                   optimizeNdpRetrieve (1),
                   optimizeIPv6AddressEntryRetrieve (2)
                 }

SrSidType ::= TEXTUAL-CONVENTION
    STATUS       current
    DESCRIPTION
        "SID Type."
    SYNTAX       INTEGER {
                   index (1),
                   label (2),
                   sid (3)
                 }

VrfTransportType ::= TEXTUAL-CONVENTION
    STATUS       current
    DESCRIPTION
        "Transport Type."
    SYNTAX      INTEGER {
                  ip (1),
                  sr (2)
                }

TilfaProtectionType ::= TEXTUAL-CONVENTION
    STATUS       current
    DESCRIPTION
        "TI-LFA Protection Type."
    SYNTAX      INTEGER {
                  link-protection (1),
                  node-protection (2)
                }


DhcpMatchType ::= TEXTUAL-CONVENTION
    STATUS        current
    DESCRIPTION
        "Dhcp Match Type."
    SYNTAX      INTEGER {
                  macAddress(1),
                  vendorClassId(2)
                }

DhcpIpAddrBindType ::= TEXTUAL-CONVENTION
    STATUS        current
    DESCRIPTION
        "Dhcp Ip Addr Bind Type."
    SYNTAX      INTEGER {
                  macAddress(1),
                  clientIdMac(2),
                  clientIdString(3),
                  hostName(4)
                }

DhcpIPv4AddrPoolActionType ::= TEXTUAL-CONVENTION
    STATUS        current
    DESCRIPTION
        "Dhcp IPv4 Addr Pool Action Type."
    SYNTAX      INTEGER {
                  notApplicable(0),
                  delLeaseAddr(1),
                  optimizeActLeaseAddrRetrieve(2)
                }

--
--  DHCP Relay Agent Table
--
f3DhcpRelayAgentTable  OBJECT-TYPE
    SYNTAX      SEQUENCE OF F3DhcpRelayAgentEntry
    MAX-ACCESS  not-accessible
    STATUS      current
    DESCRIPTION
            "A list of entries for the Dhcp Relay Agent."
    ::= { f3L3Objects 1 }

f3DhcpRelayAgentEntry  OBJECT-TYPE
    SYNTAX      F3DhcpRelayAgentEntry
    MAX-ACCESS  not-accessible
    STATUS      current
    DESCRIPTION
            "A conceptual row in the f3DhcpRelayAgentTable."
    INDEX { neIndex, f3DhcpRelayAgentIndex }
    ::= { f3DhcpRelayAgentTable 1 }

F3DhcpRelayAgentEntry ::= SEQUENCE {
    f3DhcpRelayAgentIndex                               Integer32,
    f3DhcpRelayAgentAlias                               F3DisplayString,
    f3DhcpRelayAgentAdminState                          AdminState,
    f3DhcpRelayAgentSecondaryState                      SecondaryState,
    f3DhcpRelayAgentOperationalState                    OperationalState,
    f3DhcpRelayAgentIpVersion                           IpVersion,
    f3DhcpRelayAgentServerIpAddress                     IpAddress,
    f3DhcpRelayAgentOp82SubOp9ControlEnabled            TruthValue,
    f3DhcpRelayAgentOp82SubOp9Value                     DisplayString,
    f3DhcpRelayAgentStorageType                         StorageType,
    f3DhcpRelayAgentRowStatus                           RowStatus,
    f3DhcpRelayAgentServerIpAddressList                 DisplayString
}

f3DhcpRelayAgentIndex OBJECT-TYPE
    SYNTAX      Integer32
    MAX-ACCESS  not-accessible
    STATUS      current
    DESCRIPTION
           "The index of the DHCP relay agent entry."
    ::= { f3DhcpRelayAgentEntry 1 }

f3DhcpRelayAgentAlias OBJECT-TYPE
    SYNTAX      F3DisplayString (SIZE (0..256))
    MAX-ACCESS  read-write
    STATUS      current
    DESCRIPTION
           "The DHCP relay agent alias."
    ::= { f3DhcpRelayAgentEntry 2 }

f3DhcpRelayAgentAdminState OBJECT-TYPE
    SYNTAX      AdminState
    MAX-ACCESS  read-write
    STATUS      current
    DESCRIPTION
           "The admin state of this DCHP relay agent."
    ::= { f3DhcpRelayAgentEntry 3 }

f3DhcpRelayAgentSecondaryState OBJECT-TYPE
    SYNTAX      SecondaryState
    MAX-ACCESS  read-only
    STATUS      current
    DESCRIPTION
           "The secondary state of this DCHP relay agent."
    ::= { f3DhcpRelayAgentEntry 4 }

f3DhcpRelayAgentOperationalState OBJECT-TYPE
    SYNTAX      OperationalState
    MAX-ACCESS  read-only
    STATUS      current
    DESCRIPTION
           "The operational state of this DCHP relay agent."
    ::= { f3DhcpRelayAgentEntry 5 }

f3DhcpRelayAgentIpVersion OBJECT-TYPE
    SYNTAX      IpVersion
    MAX-ACCESS  read-write
    STATUS      current
    DESCRIPTION
           "The Ip version of this DCHP relay agent."
    ::= { f3DhcpRelayAgentEntry 6 }

f3DhcpRelayAgentServerIpAddress OBJECT-TYPE
    SYNTAX      IpAddress
    MAX-ACCESS  read-write
    STATUS      current
    DESCRIPTION
           "The Ipv4 address of this DCHP relay agent."
    ::= { f3DhcpRelayAgentEntry 7 }

f3DhcpRelayAgentOp82SubOp9ControlEnabled OBJECT-TYPE
    SYNTAX      TruthValue
    MAX-ACCESS  read-write
    STATUS      current
    DESCRIPTION
           "This object describes the suboption9 of the option82 whether enabled."
    ::= { f3DhcpRelayAgentEntry 8 }

f3DhcpRelayAgentOp82SubOp9Value OBJECT-TYPE
    SYNTAX      DisplayString (SIZE (0..255))
    MAX-ACCESS  read-write
    STATUS      current
    DESCRIPTION
           "This object describes the vendor string if the suboption9 enabled."
    ::= { f3DhcpRelayAgentEntry 9 }

f3DhcpRelayAgentStorageType OBJECT-TYPE
    SYNTAX     StorageType
    MAX-ACCESS read-create
    STATUS     current
    DESCRIPTION
            "The type of storage configured for this entry."
    ::= { f3DhcpRelayAgentEntry 10 }

f3DhcpRelayAgentRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of f3DhcpRelayAgentRowStatus supported are
            createAndGo(4) and destroy(6).  All mandatory attributes
            must be specified in a single SNMP SET request with
            f3DhcpRelayAgentRowStatus value as createAndGo(4).
            Upon successful row creation, this variable has a
            value of active(1).

            The f3DhcpRelayAgentRowStatus object may be modified if
            the associated instance of this object is equal to active(1)."
    ::= { f3DhcpRelayAgentEntry 11 }

f3DhcpRelayAgentServerIpAddressList OBJECT-TYPE
    SYNTAX      DisplayString
    MAX-ACCESS  read-create
    STATUS      current
    DESCRIPTION
           "DHCP Server IP Address List(ie. 10.10.10.10,10.10.10.20)."
    ::= { f3DhcpRelayAgentEntry 12 }

--
--  VRF Table
--
f3VrfTable  OBJECT-TYPE
    SYNTAX      SEQUENCE OF F3VrfEntry
    MAX-ACCESS  not-accessible
    STATUS      current
    DESCRIPTION
            "A list of entries for the VRF user."
    ::= { f3L3Objects 2 }

f3VrfEntry  OBJECT-TYPE
    SYNTAX      F3VrfEntry
    MAX-ACCESS  not-accessible
    STATUS      current
    DESCRIPTION
            "A conceptual row in the f3VrfTable."
    INDEX { neIndex, f3VrfIndex }
    ::= { f3VrfTable 1 }

F3VrfEntry ::= SEQUENCE {
    f3VrfIndex                               Integer32,
    f3VrfAlias                               F3DisplayString,
    f3VrfAdminState                          AdminState,
    f3VrfSecondaryState                      SecondaryState,
    f3VrfOperationalState                    OperationalState,
    f3VrfAccIsolationControlEnabled          TruthValue,
    f3VrfPingIpv4Destination                 IpAddress,
    f3VrfTraceRouteIpv4Destination           IpAddress,
    f3VrfAction                              VrfAction,
    f3VrfPingResult                          F3DisplayString,
    f3VrfTraceRouteResult                    F3DisplayString,
    f3VrfStorageType                         StorageType,
    f3VrfRowStatus                           RowStatus,
    f3VrfDhcpRoutesControl                   TruthValue,
    f3VrfActionX                             VrfActionType,
    f3VrfActionIfName                        DisplayString,
    f3VrfIpVersion                           IpVersion,
    f3VrfPingIpv6Destination                 Ipv6Address,
    f3VrfTraceRouteIpv6Destination           Ipv6Address,
    f3VrfMaxFwdTableEntries                  Integer32,
    f3VrfFwdTableFull                        TruthValue,
    f3VrfEcmpDistribution                    EcmpDistributionType,
    f3VrfEcmpStaticRoutesMaximumPaths        Unsigned32,
    f3VrfTransportType                       VrfTransportType
}

f3VrfIndex OBJECT-TYPE
    SYNTAX      Integer32
    MAX-ACCESS  not-accessible
    STATUS      current
    DESCRIPTION
           "The vrf number."
    ::= { f3VrfEntry 1 }

f3VrfAlias OBJECT-TYPE
    SYNTAX      F3DisplayString (SIZE (0..256))
    MAX-ACCESS  read-write
    STATUS      current
    DESCRIPTION
           "This object describes the vrf alias."
    ::= { f3VrfEntry 2 }

f3VrfAdminState OBJECT-TYPE
    SYNTAX      AdminState
    MAX-ACCESS  read-write
    STATUS      current
    DESCRIPTION
           "This object describes the vrf admin state."
    ::= { f3VrfEntry 3 }

f3VrfSecondaryState OBJECT-TYPE
    SYNTAX      SecondaryState
    MAX-ACCESS  read-only
    STATUS      current
    DESCRIPTION
           "This object describes the vrf secondary state."
    ::= { f3VrfEntry 4 }

f3VrfOperationalState OBJECT-TYPE
    SYNTAX      OperationalState
    MAX-ACCESS  read-only
    STATUS      current
    DESCRIPTION
           "This object describes the vrf operational state."
    ::= { f3VrfEntry 5 }

f3VrfAccIsolationControlEnabled OBJECT-TYPE
    SYNTAX      OperationalState
    MAX-ACCESS  read-write
    STATUS      obsolete
    DESCRIPTION
           "This object is used to control traffic between L3 flowpoint
           on Acc port."
    ::= { f3VrfEntry 6 }

f3VrfPingIpv4Destination OBJECT-TYPE
    SYNTAX      IpAddress
    MAX-ACCESS  read-write
    STATUS      current
    DESCRIPTION
           "This object allows user to specify the IP Address to which
 	          ICMP Ping will be initiated."
    ::= { f3VrfEntry 7 }

f3VrfTraceRouteIpv4Destination OBJECT-TYPE
    SYNTAX      IpAddress
    MAX-ACCESS  read-write
    STATUS      current
    DESCRIPTION
           "This object allows user to specify the IP Address to which
          	Trace Route will be initiated."
    ::= { f3VrfEntry 8 }

f3VrfAction OBJECT-TYPE
    SYNTAX      VrfAction
    MAX-ACCESS  read-write
    STATUS      deprecated
    DESCRIPTION
           "The Vrf action, includes fluch ARP cache, ping, trace route.
            DEPRECATED and new variable to use is f3VrfActionX."
    ::= { f3VrfEntry 9 }

f3VrfPingResult OBJECT-TYPE
    SYNTAX      F3DisplayString
    MAX-ACCESS  read-only
    STATUS      current
    DESCRIPTION
           "The Ping action result."
    ::= { f3VrfEntry 10 }

f3VrfTraceRouteResult OBJECT-TYPE
    SYNTAX      F3DisplayString
    MAX-ACCESS  read-only
    STATUS      current
    DESCRIPTION
           "The trace route action result."
    ::= { f3VrfEntry 11 }

f3VrfStorageType OBJECT-TYPE
    SYNTAX     StorageType
    MAX-ACCESS read-create
    STATUS     current
    DESCRIPTION
            "The type of storage configured for this entry."
    ::= { f3VrfEntry 12 }

f3VrfRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of f3VrfRowStatus supported are
            createAndGo(4) and destroy(6).  All mandatory attributes
            must be specified in a single SNMP SET request with
            f3VrfRowStatus value as createAndGo(4).
            Upon successful row creation, this variable has a
            value of active(1).

            The f3VrfRowStatus object may be modified if
            the associated instance of this object is equal to active(1)."
    ::= { f3VrfEntry 13 }

f3VrfDhcpRoutesControl OBJECT-TYPE
    SYNTAX      TruthValue
    MAX-ACCESS  read-write
    STATUS      current
    DESCRIPTION
           "This object is used to control dynamic routes creation based on DHCP relay agent operation.
            if it is disabled, the vrf should not use host ip addresses assigned by means of DHCP relay agent
            for the dynamic routes creation."
    ::= { f3VrfEntry 14 }

f3VrfActionX OBJECT-TYPE
    SYNTAX      VrfActionType
    MAX-ACCESS  read-write
    STATUS      current
    DESCRIPTION
           "The Vrf action, includes ping, trace route and route retrieve"
    ::= { f3VrfEntry 15 }

f3VrfActionIfName OBJECT-TYPE
    SYNTAX      DisplayString
    MAX-ACCESS  read-write
    STATUS      current
    DESCRIPTION
           "Interface Name parameter for the VRF action. For example, to
            flush ARP cache for a particular interface this variable shall
            be set and then f3VrfActionX shall be set to flushArpCache."
    ::= { f3VrfEntry 16 }

f3VrfIpVersion OBJECT-TYPE
    SYNTAX      IpVersion
    MAX-ACCESS  read-create
    STATUS      current
    DESCRIPTION
           "This object describes the vrf Ip version."
    ::= { f3VrfEntry 17 }

f3VrfPingIpv6Destination OBJECT-TYPE
    SYNTAX      Ipv6Address
    MAX-ACCESS  read-write
    STATUS      current
    DESCRIPTION
           "This object allows user to specify the IP Address to which
 	          ICMP Ping will be initiated."
    ::= { f3VrfEntry 18 }

f3VrfTraceRouteIpv6Destination OBJECT-TYPE
    SYNTAX      Ipv6Address
    MAX-ACCESS  read-write
    STATUS      current
    DESCRIPTION
           "This object allows user to specify the IP Address to which
          	Trace Route will be initiated."
    ::= { f3VrfEntry 19 }

f3VrfMaxFwdTableEntries OBJECT-TYPE
    SYNTAX      Integer32
    MAX-ACCESS  read-write
    STATUS      current
    DESCRIPTION
           "This object defines the maximum forwarding 
            table entries that can be used by the vrf"
    ::= { f3VrfEntry 20 }
    
f3VrfFwdTableFull OBJECT-TYPE
    SYNTAX      TruthValue
    MAX-ACCESS  read-only
    STATUS      current
    DESCRIPTION
           "This is a status variable that indicates 
            if the forwarding table for the vrf is full"
    ::= { f3VrfEntry 21 }

f3VrfEcmpDistribution OBJECT-TYPE
    SYNTAX      EcmpDistributionType
    MAX-ACCESS  read-write
    STATUS      current
    DESCRIPTION
           "The fields in IP Packets used in hash lookup."
    ::= { f3VrfEntry 22 }

f3VrfEcmpStaticRoutesMaximumPaths OBJECT-TYPE
    SYNTAX      Unsigned32
    MAX-ACCESS  read-write
    STATUS      current
    DESCRIPTION
           "The maximum number of path used in ECMP for static routes."
    ::= { f3VrfEntry 23 }

f3VrfTransportType OBJECT-TYPE
    SYNTAX     VrfTransportType
    MAX-ACCESS read-create
    STATUS     current
    DESCRIPTION
            "The transport type of this entry."
    ::= { f3VrfEntry 24 }

--
--  L3 flowpoint Table
--
f3L3FlowPointTable  OBJECT-TYPE
    SYNTAX      SEQUENCE OF F3L3FlowPointEntry
    MAX-ACCESS  not-accessible
    STATUS      current
    DESCRIPTION
            "A list of entries for the L3 flowpoint."
    ::= { f3L3Objects 3 }

f3L3FlowPointEntry  OBJECT-TYPE
    SYNTAX      F3L3FlowPointEntry
    MAX-ACCESS  not-accessible
    STATUS      current
    DESCRIPTION
            "A conceptual row in the f3L3FlowPointTable."
    INDEX { neIndex, shelfIndex, slotIndex, f3L3FlowPointPortTypeIndex, f3L3FlowPointPortIndex, f3L3FlowPointIndex }
    ::= { f3L3FlowPointTable 1 }

F3L3FlowPointEntry ::= SEQUENCE {
    f3L3FlowPointPortTypeIndex                       Integer32,
    f3L3FlowPointPortIndex                           Integer32,
    f3L3FlowPointIndex                               Integer32,
    f3L3FlowPointAlias                               F3DisplayString,
    f3L3FlowPointAdminState                          AdminState,
    f3L3FlowPointSecondaryState                      SecondaryState,
    f3L3FlowPointOperationalState                    OperationalState,
    f3L3FlowPointMultiCOSEnabled                     TruthValue,
    f3L3FlowPointCOS                                 Integer32,
    f3L3FlowPointUntaggedMemberShipEnabled           TruthValue,
    f3L3FlowPointOuterTagMemberShipEnabled           TruthValue,
    f3L3FlowPointOuterTagMemberShipVlanId            VlanId,
    f3L3FlowPointInnerTagMemberShipEnabled           TruthValue,
    f3L3FlowPointInnerTagMemberShipVlanId            VlanId,
    f3L3FlowPointFragmentedPktsFwdEnabled            TruthValue,
    f3L3FlowPointHCosMgmtEnabled                     TruthValue,
    f3L3FlowPointHCosGuaranteedBwHi                  Unsigned32,
    f3L3FlowPointHCosGuaranteedBwLo                  Unsigned32,
    f3L3FlowPointHCosMaximumBwHi                     Unsigned32,
    f3L3FlowPointHCosMaximumBwLo                     Unsigned32,
    f3L3FlowPointPolicingEnabled                     TruthValue,
    f3L3FlowPointStorageType                         StorageType,
    f3L3FlowPointRowStatus                           RowStatus,
    f3L3FlowPointDscpOverwriteControl                TruthValue,
    f3L3FlowPointPriMapProfile                       VariablePointer,
    f3L3FlowPointRefConnectGuardFlow                 VariablePointer,
    f3L3FlowPointSecureState                         FlowSecState,
    f3L3FlowPointSecureBlockingEnabled               TruthValue,
    f3L3FlowPointWfqSegmentationCOS                  Integer32,
    f3L3FlowPointWfqGroupCOS                         Integer32,
    f3L3FlowPointWfqGroupEirLo                       Unsigned32,
    f3L3FlowPointWfqGroupEirHi                       Unsigned32,
    f3L3FlowPointOuterVlanEthertype                  Integer32,
    f3L3FlowPointInnerVlanEthertype                  Integer32,
    f3L3FlowPointIpVersion                           IpVersion
}

f3L3FlowPointPortTypeIndex OBJECT-TYPE
    SYNTAX      Integer32
    MAX-ACCESS  not-accessible
    STATUS      current
    DESCRIPTION
           "It specifies the port type, value 1 means Network Port, 
            value 2 means Access Port, value 3 means Mobile Traffic Port."
    ::= { f3L3FlowPointEntry 1 }

f3L3FlowPointPortIndex OBJECT-TYPE
    SYNTAX      Integer32
    MAX-ACCESS  not-accessible
    STATUS      current
    DESCRIPTION
           "The port number value."
    ::= { f3L3FlowPointEntry 2 }

f3L3FlowPointIndex OBJECT-TYPE
    SYNTAX      Integer32
    MAX-ACCESS  not-accessible
    STATUS      current
    DESCRIPTION
           "The L3 flow point number."
    ::= { f3L3FlowPointEntry 3 }

f3L3FlowPointAlias OBJECT-TYPE
    SYNTAX      F3DisplayString (SIZE (0..256))
    MAX-ACCESS  read-write
    STATUS      current
    DESCRIPTION
           "This object describes the L3 flow point alias."
    ::= { f3L3FlowPointEntry 4 }

f3L3FlowPointAdminState OBJECT-TYPE
    SYNTAX      AdminState
    MAX-ACCESS  read-write
    STATUS      current
    DESCRIPTION
           "This object describes the L3 flow point admin state."
    ::= { f3L3FlowPointEntry 5 }

f3L3FlowPointSecondaryState OBJECT-TYPE
    SYNTAX      SecondaryState
    MAX-ACCESS  read-only
    STATUS      current
    DESCRIPTION
           "This object describes the L3 flow point secondary state."
    ::= { f3L3FlowPointEntry 6 }

f3L3FlowPointOperationalState OBJECT-TYPE
    SYNTAX      OperationalState
    MAX-ACCESS  read-only
    STATUS      current
    DESCRIPTION
           "This object describes the L3 flow point operational state."
    ::= { f3L3FlowPointEntry 7 }

f3L3FlowPointMultiCOSEnabled OBJECT-TYPE
    SYNTAX      TruthValue
    MAX-ACCESS  read-write
    STATUS      current
    DESCRIPTION
           "Control to enable or disable per-COS BWPs on a FlowPoint.
            ENABLED:per-COS BWPs (CIR, EIR, CBS, EBS, CM, CF) are applied as a policing 
                     function for all ingress frames of this flowpoint.
            DISABLED:per-Flow BWP (CIR, EIR, CBS, EBS, CM, CF) is applied as a policing 
                     function for all ingress frames of this flowpoint.
            User must independently enable each COS BWP when ENABLED."
    ::= { f3L3FlowPointEntry 8 }

f3L3FlowPointCOS OBJECT-TYPE
    SYNTAX      Integer32
    MAX-ACCESS  read-write
    STATUS      current
    DESCRIPTION
           "Identifies the internal COS applied to all ingress frames of the flowpoint."
    ::= { f3L3FlowPointEntry 9 }

f3L3FlowPointUntaggedMemberShipEnabled OBJECT-TYPE
    SYNTAX      TruthValue
    MAX-ACCESS  read-write
    STATUS      current
    DESCRIPTION
           "This attribute controls untagged frames membership for the Flowpoint.
            ENABLED: Ingress untagged frame matches Flowpoint membership.
            DISABLED: Ingress untagged frame does not match Flowpoint membership."
    ::= { f3L3FlowPointEntry 10 }

f3L3FlowPointOuterTagMemberShipEnabled OBJECT-TYPE
    SYNTAX      TruthValue
    MAX-ACCESS  read-write
    STATUS      current
    DESCRIPTION
           "This attribute controls outer tag membership for the Flowpoint whether enabled."
    ::= { f3L3FlowPointEntry 11 }

f3L3FlowPointOuterTagMemberShipVlanId OBJECT-TYPE
    SYNTAX      VlanId
    MAX-ACCESS  read-write
    STATUS      current
    DESCRIPTION
           "This attribute controls outer tag VlanId membership for the Flowpoint."
    ::= { f3L3FlowPointEntry 12 }

f3L3FlowPointInnerTagMemberShipEnabled OBJECT-TYPE
    SYNTAX      TruthValue
    MAX-ACCESS  read-write
    STATUS      current
    DESCRIPTION
           "This attribute controls inner tag membership for the Flowpoint whether enabled."
    ::= { f3L3FlowPointEntry 13 }

f3L3FlowPointInnerTagMemberShipVlanId OBJECT-TYPE
    SYNTAX      VlanId
    MAX-ACCESS  read-write
    STATUS      current
    DESCRIPTION
           "This attribute controls inner tag VlanId membership for the Flowpoint."
    ::= { f3L3FlowPointEntry 14 }

f3L3FlowPointFragmentedPktsFwdEnabled OBJECT-TYPE
    SYNTAX      TruthValue
    MAX-ACCESS  read-write
    STATUS      current
    DESCRIPTION
           "This attribute specifies whether received IP Packets with More Fragments
            flag should be forwarded by the FlowPoint."
    ::= { f3L3FlowPointEntry 15 }

f3L3FlowPointHCosMgmtEnabled OBJECT-TYPE
    SYNTAX      TruthValue
    MAX-ACCESS  read-write
    STATUS      current
    DESCRIPTION
           "This attribute specifies whether the Hierarchical COS shaping enabled for this flow point."
    ::= { f3L3FlowPointEntry 16 }

f3L3FlowPointHCosGuaranteedBwHi OBJECT-TYPE
    SYNTAX      Unsigned32
    MAX-ACCESS  read-write
    STATUS      current
    DESCRIPTION
           "This attribute specifies the Hierarchical COS guarranteed bandwidth 
           high 32 bits for this flow point."
    ::= { f3L3FlowPointEntry 17 }

f3L3FlowPointHCosGuaranteedBwLo OBJECT-TYPE
    SYNTAX      Unsigned32
    MAX-ACCESS  read-write
    STATUS      current
    DESCRIPTION
           "This attribute specifies the Hierarchical COS guarranteed bandwidth 
           low 32 bits for this flow point."
    ::= { f3L3FlowPointEntry 18 }

f3L3FlowPointHCosMaximumBwHi OBJECT-TYPE
    SYNTAX      Unsigned32
    MAX-ACCESS  read-write
    STATUS      current
    DESCRIPTION
           "This attribute specifies the Hierarchical COS maximum bandwidth 
           high 32 bits for this flow point."
    ::= { f3L3FlowPointEntry 19 }

f3L3FlowPointHCosMaximumBwLo OBJECT-TYPE
    SYNTAX      Unsigned32
    MAX-ACCESS  read-write
    STATUS      current
    DESCRIPTION
           "This attribute specifies the Hierarchical COS maximum bandwidth 
           low 32 bits for this flow point."
    ::= { f3L3FlowPointEntry 20 }

f3L3FlowPointPolicingEnabled OBJECT-TYPE
    SYNTAX      TruthValue
    MAX-ACCESS  read-write
    STATUS      current
    DESCRIPTION
           "This attribute allows enable or disable policers of the flow point."
    ::= { f3L3FlowPointEntry 21 }

f3L3FlowPointStorageType OBJECT-TYPE
    SYNTAX     StorageType
    MAX-ACCESS read-create
    STATUS     current
    DESCRIPTION
            "The type of storage configured for this entry."
    ::= { f3L3FlowPointEntry 22 }

f3L3FlowPointRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of f3L3FlowPointRowStatus supported are
            createAndGo(4) and destroy(6).  All mandatory attributes
            must be specified in a single SNMP SET request with
            f3L3FlowPointRowStatus value as createAndGo(4).
            Upon successful row creation, this variable has a
            value of active(1).

            The f3L3FlowPointRowStatus object may be modified if
            the associated instance of this object is equal to active(1)."
    ::= { f3L3FlowPointEntry 23 }

f3L3FlowPointDscpOverwriteControl OBJECT-TYPE
    SYNTAX      TruthValue
    MAX-ACCESS  read-write
    STATUS      current
    DESCRIPTION
           "This attribute allows enable dscp value overwrite."
    ::= { f3L3FlowPointEntry 24 }

f3L3FlowPointPriMapProfile OBJECT-TYPE
    SYNTAX      VariablePointer
    MAX-ACCESS  read-write
    STATUS      current
    DESCRIPTION
           "This attribute allows specify the priority map profile."
    ::= { f3L3FlowPointEntry 25 }

f3L3FlowPointRefConnectGuardFlow OBJECT-TYPE
    SYNTAX      VariablePointer
    MAX-ACCESS  read-create
    STATUS      current
    DESCRIPTION
           "This object specifies Mac Sec flow object OID."
    ::= { f3L3FlowPointEntry 26 }

f3L3FlowPointSecureState OBJECT-TYPE
    SYNTAX      FlowSecState
    MAX-ACCESS  read-only
    STATUS      current
    DESCRIPTION
           "This object specifies the secure state of this flow."
    ::= { f3L3FlowPointEntry 27 }

f3L3FlowPointSecureBlockingEnabled OBJECT-TYPE
    SYNTAX      TruthValue
    MAX-ACCESS  read-create
    STATUS      current
    DESCRIPTION
           "This object can be used to enable/disable secure block."
    ::= { f3L3FlowPointEntry 28 }

f3L3FlowPointWfqSegmentationCOS OBJECT-TYPE
    SYNTAX      Integer32
    MAX-ACCESS  read-write
    STATUS      current
    DESCRIPTION
           "This object used to specify wfq segmentation COS value."
    ::= { f3L3FlowPointEntry 29 }

f3L3FlowPointWfqGroupCOS OBJECT-TYPE
    SYNTAX      Integer32
    MAX-ACCESS  read-write
    STATUS      current
    DESCRIPTION
           "This object used to specify wfq group COS value."
    ::= { f3L3FlowPointEntry 30 }

f3L3FlowPointWfqGroupEirLo OBJECT-TYPE
    SYNTAX      Unsigned32
    MAX-ACCESS  read-write
    STATUS      current
    DESCRIPTION
           "This object used to specify wfq group EIR low 32 bits value."
    ::= { f3L3FlowPointEntry 31 }

f3L3FlowPointWfqGroupEirHi OBJECT-TYPE
    SYNTAX      Unsigned32
    MAX-ACCESS  read-write
    STATUS      current
    DESCRIPTION
           "This object used to specify wfq group EIR high 32 bits value."
    ::= { f3L3FlowPointEntry 32 }

f3L3FlowPointOuterVlanEthertype OBJECT-TYPE
    SYNTAX     Integer32 (0..65535)
    MAX-ACCESS read-write
    STATUS     current
    DESCRIPTION
         "."
    ::= { f3L3FlowPointEntry 33 }

f3L3FlowPointInnerVlanEthertype OBJECT-TYPE
    SYNTAX     Integer32 (0..65535)
    MAX-ACCESS read-write
    STATUS     current
    DESCRIPTION
         "."
    ::= { f3L3FlowPointEntry 34 }

f3L3FlowPointIpVersion OBJECT-TYPE
    SYNTAX      IpVersion
    MAX-ACCESS  read-create
    STATUS      current
    DESCRIPTION
           "."
    ::= { f3L3FlowPointEntry 35 }


--
--  L3 ACL Rule Table
--
f3L3AclRuleTable  OBJECT-TYPE
    SYNTAX      SEQUENCE OF F3L3AclRuleEntry
    MAX-ACCESS  not-accessible
    STATUS      current
    DESCRIPTION
            "A list of entries for the L3 ACL rule."
    ::= { f3L3Objects 4 }

f3L3AclRuleEntry  OBJECT-TYPE
    SYNTAX      F3L3AclRuleEntry
    MAX-ACCESS  not-accessible
    STATUS      current
    DESCRIPTION
            "A conceptual row in the f3L3AclRuleTable."
    INDEX { neIndex, shelfIndex, slotIndex,
            f3L3FlowPointPortIndex, f3L3AclRuleParentIndex, f3L3AclRuleIndex }
    ::= { f3L3AclRuleTable 1 }

F3L3AclRuleEntry ::= SEQUENCE {
    f3L3AclRuleParentIndex                               Integer32,
    f3L3AclRuleIndex                                     Integer32,
    f3L3AclRuleAlias                                     F3DisplayString,
    f3L3AclRuleSrcIpv4AddressControl                     TruthValue,
    f3L3AclRuleDynamicSrcIpControl                       TruthValue,
    f3L3AclRuleSrcIpv4AddressLowLimit                    IpAddress,
    f3L3AclRuleDstIpv4AddressControl                     TruthValue,
    f3L3AclRuleDstIpv4AddressLowLimit                    IpAddress,
    f3L3AclRuleIpv4PriorityControl                       TruthValue,
    f3L3AclRuleIpv4PriorityLowLimit                      Integer32,
    f3L3AclRuleProtocolControl                           TruthValue,
    f3L3AclRuleProtocolNumber                            Integer32,
    f3L3AclRuleSrcPortControl                            TruthValue,
    f3L3AclRuleSrcPortLowLimit                           Integer32,
    f3L3AclRuleSrcPortHighLimit                          Integer32,
    f3L3AclRuleDstPortControl                            TruthValue,
    f3L3AclRuleDstPortLowLimit                           Integer32,
    f3L3AclRuleDstPortHighLimit                          Integer32,
    f3L3AclRulePriority                                  Integer32,
    f3L3AclRuleCOS                                       Integer32,
    f3L3AclRuleOperation                                 L3AclRuleOperation,
    f3L3AclRuleSummary                                   F3DisplayString,
    f3L3AclRuleCosOverrideControl                        TruthValue,
    f3L3AclRuleSrcMacAddressControl                      TruthValue,
    f3L3AclRuleDynamicSrcMacAddressControl               TruthValue,
    f3L3AclRuleSrcMacAddress                             MacAddress,
    f3L3AclRuleSrcMacAddressMask                         MacAddress,
    f3L3AclRuleDstMacAddressControl                      TruthValue,
    f3L3AclRuleDstMacAddress                             MacAddress,
    f3L3AclRuleDstMacAddressMask                         MacAddress,
    f3L3AclRuleOuterVlanVIDControl                       TruthValue,
    f3L3AclRuleOuterVlanVIDLowLimit                      VlanId,
    f3L3AclRuleOuterVlanVIDHighLimit                     VlanId,
    f3L3AclRuleInnerVlanVIDControl                       TruthValue,
    f3L3AclRuleInnerVlanVIDLowLimit                      VlanId,
    f3L3AclRuleInnerVlanVIDHighLimit                     VlanId,
    f3L3AclRuleOuterVlanPcpControl                       TruthValue,
    f3L3AclRuleOuterVlanPcpLowLimit                      VlanPriority,
    f3L3AclRuleOuterVlanPcpHighLimit                     VlanPriority,
    f3L3AclRuleInnerVlanPcpControl                       TruthValue,
    f3L3AclRuleInnerVlanPcpLowLimit                      VlanPriority,
    f3L3AclRuleInnerVlanPcpHighLimit                     VlanPriority,
    f3L3AclRuleOuterVlanDeiControl                       TruthValue,
    f3L3AclRuleOuterVlanDei                              Unsigned32,
    f3L3AclRuleEtherTypeControl                          TruthValue,
    f3L3AclRuleEtherType                                 Integer32,
    f3L3AclRuleTcpFlagsControl                           TruthValue,
    f3L3AclRuleTcpFlags                                  Integer32,
    f3L3AclRuleSrcIpv4AddressHighLimit                   IpAddress,
    f3L3AclRuleDstIpv4AddressHighLimit                   IpAddress,
    f3L3AclRuleIpv4PriorityHighLimit                     Integer32,
    f3L3AclRuleStorageType                               StorageType,
    f3L3AclRuleRowStatus                                 RowStatus,
    f3L3AclRuleAdminState                                AdminState,
    f3L3AclRuleActive                                    TruthValue,
    f3L3AclRuleSrcIpV6AddressControl                     TruthValue,
    f3L3AclRuleSrcIpV6Address                            Ipv6Address,
    f3L3AclRuleSrcIpV6AddressPrefixLen                   Integer32,
    f3L3AclRuleDstIpV6AddressControl                     TruthValue,
    f3L3AclRuleDstIpV6Address                            Ipv6Address,
    f3L3AclRuleDstIpV6AddressPrefixLen                   Integer32,
    f3L3AclRuleIpV6FlowLabelControl                      TruthValue,
    f3L3AclRuleIpV6FlowLabel                             Integer32,
    f3L3AclRulePriorityControl                           TruthValue,
    f3L3AclRulePriorityLowLimit                          Integer32,
    f3L3AclRulePriorityHighLimit                         Integer32
}

f3L3AclRuleParentIndex OBJECT-TYPE
    SYNTAX      Integer32
    MAX-ACCESS  not-accessible
    STATUS      current
    DESCRIPTION
           "The ACL rule parent number, it could be flow index or L3 flow point index."
    ::= { f3L3AclRuleEntry 1 }

f3L3AclRuleIndex OBJECT-TYPE
    SYNTAX      Integer32
    MAX-ACCESS  not-accessible
    STATUS      current
    DESCRIPTION
           "The ACL rule number."
    ::= { f3L3AclRuleEntry 2 }

f3L3AclRuleAlias OBJECT-TYPE
    SYNTAX      F3DisplayString (SIZE (0..256))
    MAX-ACCESS  read-write
    STATUS      current
    DESCRIPTION
           "The ACL rule alias."
    ::= { f3L3AclRuleEntry 3 }

f3L3AclRuleSrcIpv4AddressControl OBJECT-TYPE
    SYNTAX      TruthValue
    MAX-ACCESS  read-write
    STATUS      current
    DESCRIPTION
           "The ACL rule source IPv4 Adress control whether enabled."
    ::= { f3L3AclRuleEntry 4 }

f3L3AclRuleDynamicSrcIpControl OBJECT-TYPE
    SYNTAX      TruthValue
    MAX-ACCESS  read-write
    STATUS      current
    DESCRIPTION
           "The ACL rule dynamic source IPv4 or IPv6 Adress control whether enabled."
    ::= { f3L3AclRuleEntry 5 }

f3L3AclRuleSrcIpv4AddressLowLimit OBJECT-TYPE
    SYNTAX      IpAddress
    MAX-ACCESS  read-write
    STATUS      current
    DESCRIPTION
           "The ACL rule source IPv4 Adress low limit."
    ::= { f3L3AclRuleEntry 6 }

f3L3AclRuleDstIpv4AddressControl OBJECT-TYPE
    SYNTAX      TruthValue
    MAX-ACCESS  read-write
    STATUS      current
    DESCRIPTION
           "The ACL rule Destination IPv4 Adress control whether enabled."
    ::= { f3L3AclRuleEntry 7 }

f3L3AclRuleDstIpv4AddressLowLimit OBJECT-TYPE
    SYNTAX      IpAddress
    MAX-ACCESS  read-write
    STATUS      current
    DESCRIPTION
           "The ACL rule Destination IPv4 Adress low limit."
    ::= { f3L3AclRuleEntry 8 }

f3L3AclRuleIpv4PriorityControl OBJECT-TYPE
    SYNTAX      TruthValue
    MAX-ACCESS  read-write
    STATUS      deprecated
    DESCRIPTION
           "The ACL rule IPv4 Priority control whether enabled."
    ::= { f3L3AclRuleEntry 9 }

f3L3AclRuleIpv4PriorityLowLimit OBJECT-TYPE
    SYNTAX      Integer32
    MAX-ACCESS  read-write
    STATUS      deprecated
    DESCRIPTION
           "The ACL rule IPv4 priority low limit."
    ::= { f3L3AclRuleEntry 10 }

f3L3AclRuleProtocolControl OBJECT-TYPE
    SYNTAX      TruthValue
    MAX-ACCESS  read-write
    STATUS      current
    DESCRIPTION
           "The ACL rule protocol control whether enabled."
    ::= { f3L3AclRuleEntry 11 }

f3L3AclRuleProtocolNumber OBJECT-TYPE
    SYNTAX      Integer32
    MAX-ACCESS  read-write
    STATUS      current
    DESCRIPTION
           "The ACL rule protocol number."
    ::= { f3L3AclRuleEntry 12 }

f3L3AclRuleSrcPortControl OBJECT-TYPE
    SYNTAX      TruthValue
    MAX-ACCESS  read-write
    STATUS      current
    DESCRIPTION
           "The ACL rule source port whether enabled."
    ::= { f3L3AclRuleEntry 13 }

f3L3AclRuleSrcPortLowLimit OBJECT-TYPE
    SYNTAX      Integer32
    MAX-ACCESS  read-write
    STATUS      current
    DESCRIPTION
           "The ACL rule source port low limit."
    ::= { f3L3AclRuleEntry 14 }

f3L3AclRuleSrcPortHighLimit OBJECT-TYPE
    SYNTAX      Integer32
    MAX-ACCESS  read-write
    STATUS      current
    DESCRIPTION
           "The ACL rule source port low limit."
    ::= { f3L3AclRuleEntry 15 }

f3L3AclRuleDstPortControl OBJECT-TYPE
    SYNTAX      TruthValue
    MAX-ACCESS  read-write
    STATUS      current
    DESCRIPTION
           "The ACL rule destination port whether enabled."
    ::= { f3L3AclRuleEntry 16 }

f3L3AclRuleDstPortLowLimit OBJECT-TYPE
    SYNTAX      Integer32
    MAX-ACCESS  read-write
    STATUS      current
    DESCRIPTION
           "The ACL rule destination port low limit."
    ::= { f3L3AclRuleEntry 17 }

f3L3AclRuleDstPortHighLimit OBJECT-TYPE
    SYNTAX      Integer32
    MAX-ACCESS  read-write
    STATUS      current
    DESCRIPTION
           "The ACL rule destination port low limit."
    ::= { f3L3AclRuleEntry 18 }

f3L3AclRulePriority OBJECT-TYPE
    SYNTAX      Integer32
    MAX-ACCESS  read-write
    STATUS      current
    DESCRIPTION
           "The ACL rule priority."
    ::= { f3L3AclRuleEntry 19 }

f3L3AclRuleCOS OBJECT-TYPE
    SYNTAX      Integer32
    MAX-ACCESS  read-write
    STATUS      current
    DESCRIPTION
           "The ACL rule class of service."
    ::= { f3L3AclRuleEntry 20 }

f3L3AclRuleOperation OBJECT-TYPE
    SYNTAX      L3AclRuleOperation
    MAX-ACCESS  read-write
    STATUS      current
    DESCRIPTION
           "The ACL rule action."
    ::= { f3L3AclRuleEntry 21 }

f3L3AclRuleSummary OBJECT-TYPE
    SYNTAX      F3DisplayString
    MAX-ACCESS  read-only
    STATUS      current
    DESCRIPTION
           "The ACL rule summary."
    ::= { f3L3AclRuleEntry 22 }

f3L3AclRuleCosOverrideControl OBJECT-TYPE
    SYNTAX      TruthValue
    MAX-ACCESS  read-write
    STATUS      current
    DESCRIPTION
           "The ACL rule COS Override control."
    ::= { f3L3AclRuleEntry 23 }

f3L3AclRuleSrcMacAddressControl OBJECT-TYPE
    SYNTAX      TruthValue
    MAX-ACCESS  read-write
    STATUS      current
    DESCRIPTION
           "The ACL rule Source MAC address control."
    ::= { f3L3AclRuleEntry 24 }

f3L3AclRuleDynamicSrcMacAddressControl OBJECT-TYPE
    SYNTAX      TruthValue
    MAX-ACCESS  read-write
    STATUS      current
    DESCRIPTION
           "The ACL rule dynamic Source MAC address control."
    ::= { f3L3AclRuleEntry 25 }

f3L3AclRuleSrcMacAddress OBJECT-TYPE
    SYNTAX      MacAddress
    MAX-ACCESS  read-write
    STATUS      current
    DESCRIPTION
           "The ACL rule dynamic Source MAC address."
    ::= { f3L3AclRuleEntry 26 }

f3L3AclRuleSrcMacAddressMask OBJECT-TYPE
    SYNTAX      MacAddress
    MAX-ACCESS  read-write
    STATUS      current
    DESCRIPTION
           "The ACL rule dynamic Source MAC address mask."
    ::= { f3L3AclRuleEntry 27 }

f3L3AclRuleDstMacAddressControl OBJECT-TYPE
    SYNTAX      TruthValue
    MAX-ACCESS  read-write
    STATUS      current
    DESCRIPTION
           "The ACL rule dynamic Destination MAC address control."
    ::= { f3L3AclRuleEntry 28 }

f3L3AclRuleDstMacAddress OBJECT-TYPE
    SYNTAX      MacAddress
    MAX-ACCESS  read-write
    STATUS      current
    DESCRIPTION
           "The ACL rule dynamic Destination MAC address."
    ::= { f3L3AclRuleEntry 29 }

f3L3AclRuleDstMacAddressMask OBJECT-TYPE
    SYNTAX      MacAddress
    MAX-ACCESS  read-write
    STATUS      current
    DESCRIPTION
           "The ACL rule dynamic Destination MAC address mask."
    ::= { f3L3AclRuleEntry 30 }

f3L3AclRuleOuterVlanVIDControl OBJECT-TYPE
    SYNTAX      TruthValue
    MAX-ACCESS  read-write
    STATUS      current
    DESCRIPTION
           "The ACL rule outer VID control."
    ::= { f3L3AclRuleEntry 31 }

f3L3AclRuleOuterVlanVIDLowLimit OBJECT-TYPE
    SYNTAX      VlanId
    MAX-ACCESS  read-write
    STATUS      current
    DESCRIPTION
           "The ACL rule outer Vlan ID low limit."
    ::= { f3L3AclRuleEntry 32 }

f3L3AclRuleOuterVlanVIDHighLimit OBJECT-TYPE
    SYNTAX      VlanId
    MAX-ACCESS  read-write
    STATUS      current
    DESCRIPTION
           "The ACL rule outer Vlan ID high limit."
    ::= { f3L3AclRuleEntry 33 }

f3L3AclRuleInnerVlanVIDControl OBJECT-TYPE
    SYNTAX      TruthValue
    MAX-ACCESS  read-write
    STATUS      current
    DESCRIPTION
           "The ACL rule inner VID control."
    ::= { f3L3AclRuleEntry 34 }

f3L3AclRuleInnerVlanVIDLowLimit OBJECT-TYPE
    SYNTAX      VlanId
    MAX-ACCESS  read-write
    STATUS      current
    DESCRIPTION
           "The ACL rule inner Vlan ID low limit."
    ::= { f3L3AclRuleEntry 35 }

f3L3AclRuleInnerVlanVIDHighLimit OBJECT-TYPE
    SYNTAX      VlanId
    MAX-ACCESS  read-write
    STATUS      current
    DESCRIPTION
           "The ACL rule Inner Vlan ID high limit."
    ::= { f3L3AclRuleEntry 36 }

f3L3AclRuleOuterVlanPcpControl OBJECT-TYPE
    SYNTAX      TruthValue
    MAX-ACCESS  read-write
    STATUS      current
    DESCRIPTION
           "The ACL rule outer vlan PCP control."
    ::= { f3L3AclRuleEntry 37 }

f3L3AclRuleOuterVlanPcpLowLimit OBJECT-TYPE
    SYNTAX      VlanPriority
    MAX-ACCESS  read-write
    STATUS      current
    DESCRIPTION
           "The ACL rule outer vlan PCP priority low limit."
    ::= { f3L3AclRuleEntry 38 }

f3L3AclRuleOuterVlanPcpHighLimit OBJECT-TYPE
    SYNTAX      VlanPriority
    MAX-ACCESS  read-write
    STATUS      current
    DESCRIPTION
           "The ACL rule outer vlan PCP priority high limit."
    ::= { f3L3AclRuleEntry 39 }

f3L3AclRuleInnerVlanPcpControl OBJECT-TYPE
    SYNTAX      TruthValue
    MAX-ACCESS  read-write
    STATUS      current
    DESCRIPTION
           "The ACL rule inner vlan PCP control."
    ::= { f3L3AclRuleEntry 40 }

f3L3AclRuleInnerVlanPcpLowLimit OBJECT-TYPE
    SYNTAX      VlanPriority
    MAX-ACCESS  read-write
    STATUS      current
    DESCRIPTION
           "The ACL rule inner vlan PCP priority low limit."
    ::= { f3L3AclRuleEntry 41 }

f3L3AclRuleInnerVlanPcpHighLimit OBJECT-TYPE
    SYNTAX      VlanPriority
    MAX-ACCESS  read-write
    STATUS      current
    DESCRIPTION
           "The ACL rule inner vlan PCP priority high limit."
    ::= { f3L3AclRuleEntry 42 }

f3L3AclRuleOuterVlanDeiControl OBJECT-TYPE
    SYNTAX      TruthValue
    MAX-ACCESS  read-write
    STATUS      current
    DESCRIPTION
           "The ACL rule outer vlan DEI control."
    ::= { f3L3AclRuleEntry 43 }

f3L3AclRuleOuterVlanDei OBJECT-TYPE
    SYNTAX      Unsigned32 (0..1)
    MAX-ACCESS  read-write
    STATUS      current
    DESCRIPTION
           "The ACL rule outer vlan DEI."
    ::= { f3L3AclRuleEntry 44 }

f3L3AclRuleEtherTypeControl OBJECT-TYPE
    SYNTAX      TruthValue
    MAX-ACCESS  read-write
    STATUS      current
    DESCRIPTION
           "The ACL rule outer vlan ether type control."
    ::= { f3L3AclRuleEntry 45 }

f3L3AclRuleEtherType OBJECT-TYPE
    SYNTAX      Integer32
    MAX-ACCESS  read-write
    STATUS      current
    DESCRIPTION
           "The ACL rule outer vlan ether type."
    ::= { f3L3AclRuleEntry 46 }

f3L3AclRuleTcpFlagsControl OBJECT-TYPE
    SYNTAX      TruthValue
    MAX-ACCESS  read-write
    STATUS      current
    DESCRIPTION
           "The ACL rule outer vlan TCP flags control."
    ::= { f3L3AclRuleEntry 47 }

f3L3AclRuleTcpFlags OBJECT-TYPE
    SYNTAX      Integer32
    MAX-ACCESS  read-write
    STATUS      current
    DESCRIPTION
           "The ACL rule outer vlan TCP flags."
    ::= { f3L3AclRuleEntry 48 }

f3L3AclRuleSrcIpv4AddressHighLimit OBJECT-TYPE
    SYNTAX      IpAddress
    MAX-ACCESS  read-write
    STATUS      current
    DESCRIPTION
           "The ACL rule source ipv4 adress high limit."
    ::= { f3L3AclRuleEntry 49 }

f3L3AclRuleDstIpv4AddressHighLimit OBJECT-TYPE
    SYNTAX      IpAddress
    MAX-ACCESS  read-write
    STATUS      current
    DESCRIPTION
           "The ACL rule destination ipv4 adress high limit."
    ::= { f3L3AclRuleEntry 50 }

f3L3AclRuleIpv4PriorityHighLimit OBJECT-TYPE
    SYNTAX      Integer32
    MAX-ACCESS  read-write
    STATUS      deprecated
    DESCRIPTION
           "The ACL rule ipv4 priority high limit."
    ::= { f3L3AclRuleEntry 51 }

f3L3AclRuleStorageType OBJECT-TYPE
    SYNTAX      StorageType
    MAX-ACCESS  read-create
    STATUS      current
    DESCRIPTION
           "The type of storage configured for this entry."
    ::= { f3L3AclRuleEntry 52 }

f3L3AclRuleRowStatus OBJECT-TYPE
    SYNTAX      RowStatus
    MAX-ACCESS  read-create
    STATUS      current
    DESCRIPTION
           "The status of this row.
          	An entry MUST NOT exist in the active state unless all
          	objects in the entry have an appropriate value, as described
          	in the description clause for each writable object.
 	
          	The values of f3L3AclRuleRowStatus supported are
          	createAndGo(4) and destroy(6).  All mandatory attributes
          	must be specified in a single SNMP SET request with
          	f3L3AclRuleRowStatus value as createAndGo(4).
          	Upon successful row creation, this object has a
          	value of active(1).
 	
          	The f3L3AclRuleRowStatus object may be modified if
          	the associated instance of this object is equal to active(1)."
    ::= { f3L3AclRuleEntry 53 }

f3L3AclRuleAdminState  OBJECT-TYPE
    SYNTAX      AdminState
    MAX-ACCESS  read-write
    STATUS      current
    DESCRIPTION
           "This object allows user configure the Acl Rule in in-service or management state."
    ::= { f3L3AclRuleEntry 54 }

f3L3AclRuleActive OBJECT-TYPE
    SYNTAX      TruthValue
    MAX-ACCESS  read-write
    STATUS      current
    DESCRIPTION
           "The ACL Rule Active activates/deactivates ACL Rule."
    ::= { f3L3AclRuleEntry 55 }

f3L3AclRuleSrcIpV6AddressControl OBJECT-TYPE
    SYNTAX      TruthValue
    MAX-ACCESS  read-write
    STATUS      current
    DESCRIPTION
           "The ACL rule source ipv6 adress control."
    ::= { f3L3AclRuleEntry 56 }

f3L3AclRuleSrcIpV6Address OBJECT-TYPE
    SYNTAX      Ipv6Address
    MAX-ACCESS  read-write
    STATUS      current
    DESCRIPTION
           "The ACL rule source ipv6 adress."
    ::= { f3L3AclRuleEntry 57 }

f3L3AclRuleSrcIpV6AddressPrefixLen OBJECT-TYPE
    SYNTAX      Integer32 (0..128)
    MAX-ACCESS  read-write
    STATUS      current
    DESCRIPTION
           "The ACL rule source ipv6 adress prefix length."
    ::= { f3L3AclRuleEntry 58 }

f3L3AclRuleDstIpV6AddressControl OBJECT-TYPE
    SYNTAX      TruthValue
    MAX-ACCESS  read-write
    STATUS      current
    DESCRIPTION
           "The ACL rule destination ipv6 adress control."
    ::= { f3L3AclRuleEntry 59 }

f3L3AclRuleDstIpV6Address OBJECT-TYPE
    SYNTAX      Ipv6Address
    MAX-ACCESS  read-write
    STATUS      current
    DESCRIPTION
           "The ACL rule destination ipv6 adress."
    ::= { f3L3AclRuleEntry 60 }

f3L3AclRuleDstIpV6AddressPrefixLen OBJECT-TYPE
    SYNTAX      Integer32 (0..128)
    MAX-ACCESS  read-write
    STATUS      current
    DESCRIPTION
           "The ACL rule destination ipv6 adress prefix length."
    ::= { f3L3AclRuleEntry 61 }

f3L3AclRuleIpV6FlowLabelControl OBJECT-TYPE
    SYNTAX      TruthValue
    MAX-ACCESS  read-write
    STATUS      current
    DESCRIPTION
           "The ACL rule ipv6 Flow Label Control enables/disables Flow Label."
    ::= { f3L3AclRuleEntry 62 }

f3L3AclRuleIpV6FlowLabel OBJECT-TYPE
    SYNTAX      Integer32 (0..1048575)
    MAX-ACCESS  read-write
    STATUS      current
    DESCRIPTION
           "The ACL rule ipv6 Flow Label."
    ::= { f3L3AclRuleEntry 63 }

f3L3AclRulePriorityControl OBJECT-TYPE
    SYNTAX      TruthValue
    MAX-ACCESS  read-write
    STATUS      current
    DESCRIPTION
           "The ACL rule Priority control whether enabled."
    ::= { f3L3AclRuleEntry 64 }

f3L3AclRulePriorityLowLimit OBJECT-TYPE
    SYNTAX      Integer32
    MAX-ACCESS  read-write
    STATUS      current
    DESCRIPTION
           "The ACL rule priority low limit."
    ::= { f3L3AclRuleEntry 65 }

f3L3AclRulePriorityHighLimit OBJECT-TYPE
    SYNTAX      Integer32
    MAX-ACCESS  read-write
    STATUS      current
    DESCRIPTION
           "The ACL rule priority high limit."
    ::= { f3L3AclRuleEntry 66 }

--
--  L2 A2N ACL Rule Table
--
f3L2A2NAclRuleTable  OBJECT-TYPE
    SYNTAX      SEQUENCE OF F3L2A2NAclRuleEntry
    MAX-ACCESS  not-accessible
    STATUS      current
    DESCRIPTION
            "A list of entries for the L2A2N ACL rule."
    ::= { f3L3Objects 5 }

f3L2A2NAclRuleEntry  OBJECT-TYPE
    SYNTAX      F3L2A2NAclRuleEntry
    MAX-ACCESS  not-accessible
    STATUS      current
    DESCRIPTION
            "A conceptual row in the f3L2A2NAclRuleTable."
    INDEX { neIndex, shelfIndex, slotIndex,
            f3L3FlowPointPortIndex, f3L2A2NAclRuleParentIndex, f3L2A2NAclRuleIndex }
    ::= { f3L2A2NAclRuleTable 1 }

F3L2A2NAclRuleEntry ::= SEQUENCE {
    f3L2A2NAclRuleParentIndex                               Integer32,
    f3L2A2NAclRuleIndex                                     Integer32,
    f3L2A2NAclRuleAlias                                     F3DisplayString,
    f3L2A2NAclRuleSrcIpv4AddressControl                     TruthValue,
    f3L2A2NAclRuleDynamicSrcIpControl                       TruthValue,
    f3L2A2NAclRuleSrcIpv4AddressLowLimit                    IpAddress,
    f3L2A2NAclRuleDstIpv4AddressControl                     TruthValue,
    f3L2A2NAclRuleDstIpv4AddressLowLimit                    IpAddress,
    f3L2A2NAclRuleIpv4PriorityControl                       TruthValue,
    f3L2A2NAclRuleIpv4PriorityLowLimit                      Integer32,
    f3L2A2NAclRuleProtocolControl                           TruthValue,
    f3L2A2NAclRuleProtocolNumber                            Integer32,
    f3L2A2NAclRuleSrcPortControl                            TruthValue,
    f3L2A2NAclRuleSrcPortLowLimit                           Integer32,
    f3L2A2NAclRuleSrcPortHighLimit                          Integer32,
    f3L2A2NAclRuleDstPortControl                            TruthValue,
    f3L2A2NAclRuleDstPortLowLimit                           Integer32,
    f3L2A2NAclRuleDstPortHighLimit                          Integer32,
    f3L2A2NAclRulePriority                                  Integer32,
    f3L2A2NAclRuleCOS                                       Integer32,
    f3L2A2NAclRuleOperation                                 L3AclRuleOperation,
    f3L2A2NAclRuleSummary                                   F3DisplayString,
    f3L2A2NAclRuleCosOverrideControl                        TruthValue,
    f3L2A2NAclRuleSrcMacAddressControl                      TruthValue,
    f3L2A2NAclRuleDynamicSrcMacAddressControl               TruthValue,
    f3L2A2NAclRuleSrcMacAddress                             MacAddress,
    f3L2A2NAclRuleSrcMacAddressMask                         MacAddress,
    f3L2A2NAclRuleDstMacAddressControl                      TruthValue,
    f3L2A2NAclRuleDstMacAddress                             MacAddress,
    f3L2A2NAclRuleDstMacAddressMask                         MacAddress,
    f3L2A2NAclRuleOuterVlanVIDControl                       TruthValue,
    f3L2A2NAclRuleOuterVlanVIDLowLimit                      VlanId,
    f3L2A2NAclRuleOuterVlanVIDHighLimit                     VlanId,
    f3L2A2NAclRuleInnerVlanVIDControl                       TruthValue,
    f3L2A2NAclRuleInnerVlanVIDLowLimit                      VlanId,
    f3L2A2NAclRuleInnerVlanVIDHighLimit                     VlanId,
    f3L2A2NAclRuleOuterVlanPcpControl                       TruthValue,
    f3L2A2NAclRuleOuterVlanPcpLowLimit                      VlanPriority,
    f3L2A2NAclRuleOuterVlanPcpHighLimit                     VlanPriority,
    f3L2A2NAclRuleInnerVlanPcpControl                       TruthValue,
    f3L2A2NAclRuleInnerVlanPcpLowLimit                      VlanPriority,
    f3L2A2NAclRuleInnerVlanPcpHighLimit                     VlanPriority,
    f3L2A2NAclRuleOuterVlanDeiControl                       TruthValue,
    f3L2A2NAclRuleOuterVlanDei                              Unsigned32,
    f3L2A2NAclRuleEtherTypeControl                          TruthValue,
    f3L2A2NAclRuleEtherType                                 Integer32,
    f3L2A2NAclRuleTcpFlagsControl                           TruthValue,
    f3L2A2NAclRuleTcpFlags                                  Integer32,
    f3L2A2NAclRuleSrcIpv4AddressHighLimit                   IpAddress,
    f3L2A2NAclRuleDstIpv4AddressHighLimit                   IpAddress,
    f3L2A2NAclRuleIpv4PriorityHighLimit                     Integer32,
    f3L2A2NAclRuleStorageType                               StorageType,
    f3L2A2NAclRuleRowStatus                                 RowStatus,
    f3L2A2NAclRuleAdminState                                AdminState,
    f3L2A2NAclRuleActive                                    TruthValue,
    f3L2A2NAclRuleSrcIpV6AddressControl                     TruthValue,
    f3L2A2NAclRuleSrcIpV6Address                            Ipv6Address,
    f3L2A2NAclRuleSrcIpV6AddressPrefixLen                   Integer32,
    f3L2A2NAclRuleDstIpV6AddressControl                     TruthValue,
    f3L2A2NAclRuleDstIpV6Address                            Ipv6Address,
    f3L2A2NAclRuleDstIpV6AddressPrefixLen                   Integer32,
    f3L2A2NAclRuleIpV6FlowLabelControl                      TruthValue,
    f3L2A2NAclRuleIpV6FlowLabel                             Integer32
}

f3L2A2NAclRuleParentIndex OBJECT-TYPE
    SYNTAX      Integer32
    MAX-ACCESS  not-accessible
    STATUS      current
    DESCRIPTION
           "The ACL rule parent number, it could be flow index"
    ::= { f3L2A2NAclRuleEntry 1 }

f3L2A2NAclRuleIndex OBJECT-TYPE
    SYNTAX      Integer32
    MAX-ACCESS  not-accessible
    STATUS      current
    DESCRIPTION
           "The ACL rule number."
    ::= { f3L2A2NAclRuleEntry 2 }

f3L2A2NAclRuleAlias OBJECT-TYPE
    SYNTAX      F3DisplayString (SIZE (0..256))
    MAX-ACCESS  read-write
    STATUS      current
    DESCRIPTION
           "The ACL rule alias."
    ::= { f3L2A2NAclRuleEntry 3 }

f3L2A2NAclRuleSrcIpv4AddressControl OBJECT-TYPE
    SYNTAX      TruthValue
    MAX-ACCESS  read-write
    STATUS      current
    DESCRIPTION
           "The ACL rule source IPv4 Adress control whether enabled."
    ::= { f3L2A2NAclRuleEntry 4 }

f3L2A2NAclRuleDynamicSrcIpControl OBJECT-TYPE
    SYNTAX      TruthValue
    MAX-ACCESS  read-write
    STATUS      current
    DESCRIPTION
           "The ACL rule dynamic source IPv4 or IPv6 Adress control whether enabled."
    ::= { f3L2A2NAclRuleEntry 5 }

f3L2A2NAclRuleSrcIpv4AddressLowLimit OBJECT-TYPE
    SYNTAX      IpAddress
    MAX-ACCESS  read-write
    STATUS      current
    DESCRIPTION
           "The ACL rule source IPv4 Adress low limit."
    ::= { f3L2A2NAclRuleEntry 6 }

f3L2A2NAclRuleDstIpv4AddressControl OBJECT-TYPE
    SYNTAX      TruthValue
    MAX-ACCESS  read-write
    STATUS      current
    DESCRIPTION
           "The ACL rule Destination IPv4 Adress control whether enabled."
    ::= { f3L2A2NAclRuleEntry 7 }

f3L2A2NAclRuleDstIpv4AddressLowLimit OBJECT-TYPE
    SYNTAX      IpAddress
    MAX-ACCESS  read-write
    STATUS      current
    DESCRIPTION
           "The ACL rule Destination IPv4 Adress low limit."
    ::= { f3L2A2NAclRuleEntry 8 }

f3L2A2NAclRuleIpv4PriorityControl OBJECT-TYPE
    SYNTAX      TruthValue
    MAX-ACCESS  read-write
    STATUS      current
    DESCRIPTION
           "The ACL rule IPv4 Priority control whether enabled."
    ::= { f3L2A2NAclRuleEntry 9 }

f3L2A2NAclRuleIpv4PriorityLowLimit OBJECT-TYPE
    SYNTAX      Integer32
    MAX-ACCESS  read-write
    STATUS      current
    DESCRIPTION
           "The ACL rule IPv4 priority low limit."
    ::= { f3L2A2NAclRuleEntry 10 }

f3L2A2NAclRuleProtocolControl OBJECT-TYPE
    SYNTAX      TruthValue
    MAX-ACCESS  read-write
    STATUS      current
    DESCRIPTION
           "The ACL rule protocol control whether enabled."
    ::= { f3L2A2NAclRuleEntry 11 }

f3L2A2NAclRuleProtocolNumber OBJECT-TYPE
    SYNTAX      Integer32
    MAX-ACCESS  read-write
    STATUS      current
    DESCRIPTION
           "The ACL rule protocol number."
    ::= { f3L2A2NAclRuleEntry 12 }

f3L2A2NAclRuleSrcPortControl OBJECT-TYPE
    SYNTAX      TruthValue
    MAX-ACCESS  read-write
    STATUS      current
    DESCRIPTION
           "The ACL rule source port whether enabled."
    ::= { f3L2A2NAclRuleEntry 13 }

f3L2A2NAclRuleSrcPortLowLimit OBJECT-TYPE
    SYNTAX      Integer32
    MAX-ACCESS  read-write
    STATUS      current
    DESCRIPTION
           "The ACL rule source port low limit."
    ::= { f3L2A2NAclRuleEntry 14 }

f3L2A2NAclRuleSrcPortHighLimit OBJECT-TYPE
    SYNTAX      Integer32
    MAX-ACCESS  read-write
    STATUS      current
    DESCRIPTION
           "The ACL rule source port low limit."
    ::= { f3L2A2NAclRuleEntry 15 }

f3L2A2NAclRuleDstPortControl OBJECT-TYPE
    SYNTAX      TruthValue
    MAX-ACCESS  read-write
    STATUS      current
    DESCRIPTION
           "The ACL rule destination port whether enabled."
    ::= { f3L2A2NAclRuleEntry 16 }

f3L2A2NAclRuleDstPortLowLimit OBJECT-TYPE
    SYNTAX      Integer32
    MAX-ACCESS  read-write
    STATUS      current
    DESCRIPTION
           "The ACL rule destination port low limit."
    ::= { f3L2A2NAclRuleEntry 17 }

f3L2A2NAclRuleDstPortHighLimit OBJECT-TYPE
    SYNTAX      Integer32
    MAX-ACCESS  read-write
    STATUS      current
    DESCRIPTION
           "The ACL rule destination port low limit."
    ::= { f3L2A2NAclRuleEntry 18 }

f3L2A2NAclRulePriority OBJECT-TYPE
    SYNTAX      Integer32
    MAX-ACCESS  read-write
    STATUS      current
    DESCRIPTION
           "The ACL rule priority."
    ::= { f3L2A2NAclRuleEntry 19 }

f3L2A2NAclRuleCOS OBJECT-TYPE
    SYNTAX      Integer32
    MAX-ACCESS  read-write
    STATUS      current
    DESCRIPTION
           "The ACL rule class of service."
    ::= { f3L2A2NAclRuleEntry 20 }

f3L2A2NAclRuleOperation OBJECT-TYPE
    SYNTAX      L3AclRuleOperation
    MAX-ACCESS  read-write
    STATUS      current
    DESCRIPTION
           "The ACL rule action."
    ::= { f3L2A2NAclRuleEntry 21 }

f3L2A2NAclRuleSummary OBJECT-TYPE
    SYNTAX      F3DisplayString
    MAX-ACCESS  read-only
    STATUS      current
    DESCRIPTION
           "The ACL rule summary."
    ::= { f3L2A2NAclRuleEntry 22 }

f3L2A2NAclRuleCosOverrideControl OBJECT-TYPE
    SYNTAX      TruthValue
    MAX-ACCESS  read-write
    STATUS      current
    DESCRIPTION
           "The ACL rule COS Override control."
    ::= { f3L2A2NAclRuleEntry 23 }

f3L2A2NAclRuleSrcMacAddressControl OBJECT-TYPE
    SYNTAX      TruthValue
    MAX-ACCESS  read-write
    STATUS      current
    DESCRIPTION
           "The ACL rule Source MAC address control."
    ::= { f3L2A2NAclRuleEntry 24 }

f3L2A2NAclRuleDynamicSrcMacAddressControl OBJECT-TYPE
    SYNTAX      TruthValue
    MAX-ACCESS  read-write
    STATUS      current
    DESCRIPTION
           "The ACL rule dynamic Source MAC address control."
    ::= { f3L2A2NAclRuleEntry 25 }

f3L2A2NAclRuleSrcMacAddress OBJECT-TYPE
    SYNTAX      MacAddress
    MAX-ACCESS  read-write
    STATUS      current
    DESCRIPTION
           "The ACL rule dynamic Source MAC address."
    ::= { f3L2A2NAclRuleEntry 26 }

f3L2A2NAclRuleSrcMacAddressMask OBJECT-TYPE
    SYNTAX      MacAddress
    MAX-ACCESS  read-write
    STATUS      current
    DESCRIPTION
           "The ACL rule dynamic Source MAC address mask."
    ::= { f3L2A2NAclRuleEntry 27 }

f3L2A2NAclRuleDstMacAddressControl OBJECT-TYPE
    SYNTAX      TruthValue
    MAX-ACCESS  read-write
    STATUS      current
    DESCRIPTION
           "The ACL rule dynamic Destination MAC address control."
    ::= { f3L2A2NAclRuleEntry 28 }

f3L2A2NAclRuleDstMacAddress OBJECT-TYPE
    SYNTAX      MacAddress
    MAX-ACCESS  read-write
    STATUS      current
    DESCRIPTION
           "The ACL rule dynamic Destination MAC address."
    ::= { f3L2A2NAclRuleEntry 29 }

f3L2A2NAclRuleDstMacAddressMask OBJECT-TYPE
    SYNTAX      MacAddress
    MAX-ACCESS  read-write
    STATUS      current
    DESCRIPTION
           "The ACL rule dynamic Destination MAC address mask."
    ::= { f3L2A2NAclRuleEntry 30 }

f3L2A2NAclRuleOuterVlanVIDControl OBJECT-TYPE
    SYNTAX      TruthValue
    MAX-ACCESS  read-write
    STATUS      current
    DESCRIPTION
           "The ACL rule outer VID control."
    ::= { f3L2A2NAclRuleEntry 31 }

f3L2A2NAclRuleOuterVlanVIDLowLimit OBJECT-TYPE
    SYNTAX      VlanId
    MAX-ACCESS  read-write
    STATUS      current
    DESCRIPTION
           "The ACL rule outer Vlan ID low limit."
    ::= { f3L2A2NAclRuleEntry 32 }

f3L2A2NAclRuleOuterVlanVIDHighLimit OBJECT-TYPE
    SYNTAX      VlanId
    MAX-ACCESS  read-write
    STATUS      current
    DESCRIPTION
           "The ACL rule outer Vlan ID high limit."
    ::= { f3L2A2NAclRuleEntry 33 }

f3L2A2NAclRuleInnerVlanVIDControl OBJECT-TYPE
    SYNTAX      TruthValue
    MAX-ACCESS  read-write
    STATUS      current
    DESCRIPTION
           "The ACL rule inner VID control."
    ::= { f3L2A2NAclRuleEntry 34 }

f3L2A2NAclRuleInnerVlanVIDLowLimit OBJECT-TYPE
    SYNTAX      VlanId
    MAX-ACCESS  read-write
    STATUS      current
    DESCRIPTION
           "The ACL rule inner Vlan ID low limit."
    ::= { f3L2A2NAclRuleEntry 35 }

f3L2A2NAclRuleInnerVlanVIDHighLimit OBJECT-TYPE
    SYNTAX      VlanId
    MAX-ACCESS  read-write
    STATUS      current
    DESCRIPTION
           "The ACL rule Inner Vlan ID high limit."
    ::= { f3L2A2NAclRuleEntry 36 }

f3L2A2NAclRuleOuterVlanPcpControl OBJECT-TYPE
    SYNTAX      TruthValue
    MAX-ACCESS  read-write
    STATUS      current
    DESCRIPTION
           "The ACL rule outer vlan PCP control."
    ::= { f3L2A2NAclRuleEntry 37 }

f3L2A2NAclRuleOuterVlanPcpLowLimit OBJECT-TYPE
    SYNTAX      VlanPriority
    MAX-ACCESS  read-write
    STATUS      current
    DESCRIPTION
           "The ACL rule outer vlan PCP priority low limit."
    ::= { f3L2A2NAclRuleEntry 38 }

f3L2A2NAclRuleOuterVlanPcpHighLimit OBJECT-TYPE
    SYNTAX      VlanPriority
    MAX-ACCESS  read-write
    STATUS      current
    DESCRIPTION
           "The ACL rule outer vlan PCP priority high limit."
    ::= { f3L2A2NAclRuleEntry 39 }

f3L2A2NAclRuleInnerVlanPcpControl OBJECT-TYPE
    SYNTAX      TruthValue
    MAX-ACCESS  read-write
    STATUS      current
    DESCRIPTION
           "The ACL rule inner vlan PCP control."
    ::= { f3L2A2NAclRuleEntry 40 }

f3L2A2NAclRuleInnerVlanPcpLowLimit OBJECT-TYPE
    SYNTAX      VlanPriority
    MAX-ACCESS  read-write
    STATUS      current
    DESCRIPTION
           "The ACL rule inner vlan PCP priority low limit."
    ::= { f3L2A2NAclRuleEntry 41 }

f3L2A2NAclRuleInnerVlanPcpHighLimit OBJECT-TYPE
    SYNTAX      VlanPriority
    MAX-ACCESS  read-write
    STATUS      current
    DESCRIPTION
           "The ACL rule inner vlan PCP priority high limit."
    ::= { f3L2A2NAclRuleEntry 42 }

f3L2A2NAclRuleOuterVlanDeiControl OBJECT-TYPE
    SYNTAX      TruthValue
    MAX-ACCESS  read-write
    STATUS      current
    DESCRIPTION
           "The ACL rule outer vlan DEI control."
    ::= { f3L2A2NAclRuleEntry 43 }

f3L2A2NAclRuleOuterVlanDei OBJECT-TYPE
    SYNTAX      Unsigned32 (0..1)
    MAX-ACCESS  read-write
    STATUS      current
    DESCRIPTION
           "The ACL rule outer vlan DEI."
    ::= { f3L2A2NAclRuleEntry 44 }

f3L2A2NAclRuleEtherTypeControl OBJECT-TYPE
    SYNTAX      TruthValue
    MAX-ACCESS  read-write
    STATUS      current
    DESCRIPTION
           "The ACL rule outer vlan ether type control."
    ::= { f3L2A2NAclRuleEntry 45 }

f3L2A2NAclRuleEtherType OBJECT-TYPE
    SYNTAX      Integer32
    MAX-ACCESS  read-write
    STATUS      current
    DESCRIPTION
           "The ACL rule outer vlan ether type."
    ::= { f3L2A2NAclRuleEntry 46 }

f3L2A2NAclRuleTcpFlagsControl OBJECT-TYPE
    SYNTAX      TruthValue
    MAX-ACCESS  read-write
    STATUS      current
    DESCRIPTION
           "The ACL rule outer vlan TCP flags control."
    ::= { f3L2A2NAclRuleEntry 47 }

f3L2A2NAclRuleTcpFlags OBJECT-TYPE
    SYNTAX      Integer32
    MAX-ACCESS  read-write
    STATUS      current
    DESCRIPTION
           "The ACL rule outer vlan TCP flags."
    ::= { f3L2A2NAclRuleEntry 48 }

f3L2A2NAclRuleSrcIpv4AddressHighLimit OBJECT-TYPE
    SYNTAX      IpAddress
    MAX-ACCESS  read-write
    STATUS      current
    DESCRIPTION
           "The ACL rule source ipv4 adress high limit."
    ::= { f3L2A2NAclRuleEntry 49 }

f3L2A2NAclRuleDstIpv4AddressHighLimit OBJECT-TYPE
    SYNTAX      IpAddress
    MAX-ACCESS  read-write
    STATUS      current
    DESCRIPTION
           "The ACL rule destination ipv4 adress high limit."
    ::= { f3L2A2NAclRuleEntry 50 }

f3L2A2NAclRuleIpv4PriorityHighLimit OBJECT-TYPE
    SYNTAX      Integer32
    MAX-ACCESS  read-write
    STATUS      current
    DESCRIPTION
           "The ACL rule ipv4 priority high limit."
    ::= { f3L2A2NAclRuleEntry 51 }

f3L2A2NAclRuleStorageType OBJECT-TYPE
    SYNTAX      StorageType
    MAX-ACCESS  read-create
    STATUS      current
    DESCRIPTION
           "The type of storage configured for this entry."
    ::= { f3L2A2NAclRuleEntry 52 }

f3L2A2NAclRuleRowStatus OBJECT-TYPE
    SYNTAX      RowStatus
    MAX-ACCESS  read-create
    STATUS      current
    DESCRIPTION
           "The status of this row.
          	An entry MUST NOT exist in the active state unless all
          	objects in the entry have an appropriate value, as described
          	in the description clause for each writable object.
 	
          	The values of f3L2A2NAclRuleRowStatus supported are
          	createAndGo(4) and destroy(6).  All mandatory attributes
          	must be specified in a single SNMP SET request with
          	f3L2A2NAclRuleRowStatus value as createAndGo(4).
          	Upon successful row creation, this object has a
          	value of active(1).
 	
          	The f3L2A2NAclRuleRowStatus object may be modified if
          	the associated instance of this object is equal to active(1)."
    ::= { f3L2A2NAclRuleEntry 53 }

f3L2A2NAclRuleAdminState OBJECT-TYPE
    SYNTAX      AdminState
    MAX-ACCESS  read-write
    STATUS      current
    DESCRIPTION
           "This object allows user configure the Acl Rule in-service or management state."
    ::= { f3L2A2NAclRuleEntry 54 }

f3L2A2NAclRuleActive OBJECT-TYPE
    SYNTAX      TruthValue
    MAX-ACCESS  read-write
    STATUS      current
    DESCRIPTION
           "The ACL rule active control."
    ::= { f3L2A2NAclRuleEntry 55 }

f3L2A2NAclRuleSrcIpV6AddressControl OBJECT-TYPE
    SYNTAX      TruthValue
    MAX-ACCESS  read-write
    STATUS      current
    DESCRIPTION
           "The ACL rule source ipv6 adress control."
    ::= { f3L2A2NAclRuleEntry 56 }

f3L2A2NAclRuleSrcIpV6Address OBJECT-TYPE
    SYNTAX      Ipv6Address
    MAX-ACCESS  read-write
    STATUS      current
    DESCRIPTION
           "The ACL rule source ipv6 adress."
    ::= { f3L2A2NAclRuleEntry 57 }

f3L2A2NAclRuleSrcIpV6AddressPrefixLen OBJECT-TYPE
    SYNTAX      Integer32
    MAX-ACCESS  read-write
    STATUS      current
    DESCRIPTION
           "The ACL rule source ipv6 adress prefix length."
    ::= { f3L2A2NAclRuleEntry 58 }

f3L2A2NAclRuleDstIpV6AddressControl OBJECT-TYPE
    SYNTAX      TruthValue
    MAX-ACCESS  read-write
    STATUS      current
    DESCRIPTION
           "The ACL rule destination ipv6 adress control."
    ::= { f3L2A2NAclRuleEntry 59 }

f3L2A2NAclRuleDstIpV6Address OBJECT-TYPE
    SYNTAX      Ipv6Address
    MAX-ACCESS  read-write
    STATUS      current
    DESCRIPTION
           "The ACL rule destination ipv6 adress."
    ::= { f3L2A2NAclRuleEntry 60 }

f3L2A2NAclRuleDstIpV6AddressPrefixLen OBJECT-TYPE
    SYNTAX      Integer32
    MAX-ACCESS  read-write
    STATUS      current
    DESCRIPTION
           "The ACL rule destination ipv6 adress prefix length."
    ::= { f3L2A2NAclRuleEntry 61 }

f3L2A2NAclRuleIpV6FlowLabelControl OBJECT-TYPE
    SYNTAX      TruthValue
    MAX-ACCESS  read-write
    STATUS      current
    DESCRIPTION
           "The ACL rule IPv6 flow lable control."
    ::= { f3L2A2NAclRuleEntry 62 }

f3L2A2NAclRuleIpV6FlowLabel OBJECT-TYPE
    SYNTAX      Integer32
    MAX-ACCESS  read-write
    STATUS      current
    DESCRIPTION
           "The ACL rule IPv6 flow lable."
    ::= { f3L2A2NAclRuleEntry 63 }


--
--  L2 N2A ACL Rule Table
--
f3L2N2AAclRuleTable  OBJECT-TYPE
    SYNTAX      SEQUENCE OF F3L2N2AAclRuleEntry
    MAX-ACCESS  not-accessible
    STATUS      current
    DESCRIPTION
            "A list of entries for the L2N2A ACL rule."
    ::= { f3L3Objects 6 }

f3L2N2AAclRuleEntry  OBJECT-TYPE
    SYNTAX      F3L2N2AAclRuleEntry
    MAX-ACCESS  not-accessible
    STATUS      current
    DESCRIPTION
            "A conceptual row in the f3L2N2AAclRuleTable."
    INDEX { neIndex, shelfIndex, slotIndex,
            f3L3FlowPointPortIndex, f3L2N2AAclRuleParentIndex, f3L2N2AAclRuleIndex }
    ::= { f3L2N2AAclRuleTable 1 }

F3L2N2AAclRuleEntry ::= SEQUENCE {
    f3L2N2AAclRuleParentIndex                               Integer32,
    f3L2N2AAclRuleIndex                                     Integer32,
    f3L2N2AAclRuleAlias                                     F3DisplayString,
    f3L2N2AAclRuleSrcIpv4AddressControl                     TruthValue,
    f3L2N2AAclRuleDynamicSrcIpControl                       TruthValue,
    f3L2N2AAclRuleSrcIpv4AddressLowLimit                    IpAddress,
    f3L2N2AAclRuleDstIpv4AddressControl                     TruthValue,
    f3L2N2AAclRuleDstIpv4AddressLowLimit                    IpAddress,
    f3L2N2AAclRuleIpv4PriorityControl                       TruthValue,
    f3L2N2AAclRuleIpv4PriorityLowLimit                      Integer32,
    f3L2N2AAclRuleProtocolControl                           TruthValue,
    f3L2N2AAclRuleProtocolNumber                            Integer32,
    f3L2N2AAclRuleSrcPortControl                            TruthValue,
    f3L2N2AAclRuleSrcPortLowLimit                           Integer32,
    f3L2N2AAclRuleSrcPortHighLimit                          Integer32,
    f3L2N2AAclRuleDstPortControl                            TruthValue,
    f3L2N2AAclRuleDstPortLowLimit                           Integer32,
    f3L2N2AAclRuleDstPortHighLimit                          Integer32,
    f3L2N2AAclRulePriority                                  Integer32,
    f3L2N2AAclRuleCOS                                       Integer32,
    f3L2N2AAclRuleOperation                                 L3AclRuleOperation,
    f3L2N2AAclRuleSummary                                   F3DisplayString,
    f3L2N2AAclRuleCosOverrideControl                        TruthValue,
    f3L2N2AAclRuleSrcMacAddressControl                      TruthValue,
    f3L2N2AAclRuleDynamicSrcMacAddressControl               TruthValue,
    f3L2N2AAclRuleSrcMacAddress                             MacAddress,
    f3L2N2AAclRuleSrcMacAddressMask                         MacAddress,
    f3L2N2AAclRuleDstMacAddressControl                      TruthValue,
    f3L2N2AAclRuleDstMacAddress                             MacAddress,
    f3L2N2AAclRuleDstMacAddressMask                         MacAddress,
    f3L2N2AAclRuleOuterVlanVIDControl                       TruthValue,
    f3L2N2AAclRuleOuterVlanVIDLowLimit                      VlanId,
    f3L2N2AAclRuleOuterVlanVIDHighLimit                     VlanId,
    f3L2N2AAclRuleInnerVlanVIDControl                       TruthValue,
    f3L2N2AAclRuleInnerVlanVIDLowLimit                      VlanId,
    f3L2N2AAclRuleInnerVlanVIDHighLimit                     VlanId,
    f3L2N2AAclRuleOuterVlanPcpControl                       TruthValue,
    f3L2N2AAclRuleOuterVlanPcpLowLimit                      VlanPriority,
    f3L2N2AAclRuleOuterVlanPcpHighLimit                     VlanPriority,
    f3L2N2AAclRuleInnerVlanPcpControl                       TruthValue,
    f3L2N2AAclRuleInnerVlanPcpLowLimit                      VlanPriority,
    f3L2N2AAclRuleInnerVlanPcpHighLimit                     VlanPriority,
    f3L2N2AAclRuleOuterVlanDeiControl                       TruthValue,
    f3L2N2AAclRuleOuterVlanDei                              Unsigned32,
    f3L2N2AAclRuleEtherTypeControl                          TruthValue,
    f3L2N2AAclRuleEtherType                                 Integer32,
    f3L2N2AAclRuleTcpFlagsControl                           TruthValue,
    f3L2N2AAclRuleTcpFlags                                  Integer32,
    f3L2N2AAclRuleSrcIpv4AddressHighLimit                   IpAddress,
    f3L2N2AAclRuleDstIpv4AddressHighLimit                   IpAddress,
    f3L2N2AAclRuleIpv4PriorityHighLimit                     Integer32,
    f3L2N2AAclRuleStorageType                               StorageType,
    f3L2N2AAclRuleRowStatus                                 RowStatus,
    f3L2N2AAclRuleAdminState                                AdminState,
    f3L2N2AAclRuleActive                                    TruthValue,
    f3L2N2AAclRuleSrcIpV6AddressControl                     TruthValue,
    f3L2N2AAclRuleSrcIpV6Address                            Ipv6Address,
    f3L2N2AAclRuleSrcIpV6AddressPrefixLen                   Integer32,
    f3L2N2AAclRuleDstIpV6AddressControl                     TruthValue,
    f3L2N2AAclRuleDstIpV6Address                            Ipv6Address,
    f3L2N2AAclRuleDstIpV6AddressPrefixLen                   Integer32,
    f3L2N2AAclRuleIpV6FlowLabelControl                      TruthValue,
    f3L2N2AAclRuleIpV6FlowLabel                             Integer32
}

f3L2N2AAclRuleParentIndex OBJECT-TYPE
    SYNTAX      Integer32
    MAX-ACCESS  not-accessible
    STATUS      current
    DESCRIPTION
           "The ACL rule parent number, it could be flow index"
    ::= { f3L2N2AAclRuleEntry 1 }

f3L2N2AAclRuleIndex OBJECT-TYPE
    SYNTAX      Integer32
    MAX-ACCESS  not-accessible
    STATUS      current
    DESCRIPTION
           "The ACL rule number."
    ::= { f3L2N2AAclRuleEntry 2 }

f3L2N2AAclRuleAlias OBJECT-TYPE
    SYNTAX      F3DisplayString (SIZE (0..256))
    MAX-ACCESS  read-write
    STATUS      current
    DESCRIPTION
           "The ACL rule alias."
    ::= { f3L2N2AAclRuleEntry 3 }

f3L2N2AAclRuleSrcIpv4AddressControl OBJECT-TYPE
    SYNTAX      TruthValue
    MAX-ACCESS  read-write
    STATUS      current
    DESCRIPTION
           "The ACL rule source IPv4 Adress control whether enabled."
    ::= { f3L2N2AAclRuleEntry 4 }

f3L2N2AAclRuleDynamicSrcIpControl OBJECT-TYPE
    SYNTAX      TruthValue
    MAX-ACCESS  read-write
    STATUS      current
    DESCRIPTION
           "The ACL rule dynamic source IPv4 or IPv6 Adress control whether enabled."
    ::= { f3L2N2AAclRuleEntry 5 }

f3L2N2AAclRuleSrcIpv4AddressLowLimit OBJECT-TYPE
    SYNTAX      IpAddress
    MAX-ACCESS  read-write
    STATUS      current
    DESCRIPTION
           "The ACL rule source IPv4 Adress low limit."
    ::= { f3L2N2AAclRuleEntry 6 }

f3L2N2AAclRuleDstIpv4AddressControl OBJECT-TYPE
    SYNTAX      TruthValue
    MAX-ACCESS  read-write
    STATUS      current
    DESCRIPTION
           "The ACL rule Destination IPv4 Adress control whether enabled."
    ::= { f3L2N2AAclRuleEntry 7 }

f3L2N2AAclRuleDstIpv4AddressLowLimit OBJECT-TYPE
    SYNTAX      IpAddress
    MAX-ACCESS  read-write
    STATUS      current
    DESCRIPTION
           "The ACL rule Destination IPv4 Adress low limit."
    ::= { f3L2N2AAclRuleEntry 8 }

f3L2N2AAclRuleIpv4PriorityControl OBJECT-TYPE
    SYNTAX      TruthValue
    MAX-ACCESS  read-write
    STATUS      current
    DESCRIPTION
           "The ACL rule IPv4 Priority control whether enabled."
    ::= { f3L2N2AAclRuleEntry 9 }

f3L2N2AAclRuleIpv4PriorityLowLimit OBJECT-TYPE
    SYNTAX      Integer32
    MAX-ACCESS  read-write
    STATUS      current
    DESCRIPTION
           "The ACL rule IPv4 priority low limit."
    ::= { f3L2N2AAclRuleEntry 10 }

f3L2N2AAclRuleProtocolControl OBJECT-TYPE
    SYNTAX      TruthValue
    MAX-ACCESS  read-write
    STATUS      current
    DESCRIPTION
           "The ACL rule protocol control whether enabled."
    ::= { f3L2N2AAclRuleEntry 11 }

f3L2N2AAclRuleProtocolNumber OBJECT-TYPE
    SYNTAX      Integer32
    MAX-ACCESS  read-write
    STATUS      current
    DESCRIPTION
           "The ACL rule protocol number."
    ::= { f3L2N2AAclRuleEntry 12 }

f3L2N2AAclRuleSrcPortControl OBJECT-TYPE
    SYNTAX      TruthValue
    MAX-ACCESS  read-write
    STATUS      current
    DESCRIPTION
           "The ACL rule source port whether enabled."
    ::= { f3L2N2AAclRuleEntry 13 }

f3L2N2AAclRuleSrcPortLowLimit OBJECT-TYPE
    SYNTAX      Integer32
    MAX-ACCESS  read-write
    STATUS      current
    DESCRIPTION
           "The ACL rule source port low limit."
    ::= { f3L2N2AAclRuleEntry 14 }

f3L2N2AAclRuleSrcPortHighLimit OBJECT-TYPE
    SYNTAX      Integer32
    MAX-ACCESS  read-write
    STATUS      current
    DESCRIPTION
           "The ACL rule source port low limit."
    ::= { f3L2N2AAclRuleEntry 15 }

f3L2N2AAclRuleDstPortControl OBJECT-TYPE
    SYNTAX      TruthValue
    MAX-ACCESS  read-write
    STATUS      current
    DESCRIPTION
           "The ACL rule destination port whether enabled."
    ::= { f3L2N2AAclRuleEntry 16 }

f3L2N2AAclRuleDstPortLowLimit OBJECT-TYPE
    SYNTAX      Integer32
    MAX-ACCESS  read-write
    STATUS      current
    DESCRIPTION
           "The ACL rule destination port low limit."
    ::= { f3L2N2AAclRuleEntry 17 }

f3L2N2AAclRuleDstPortHighLimit OBJECT-TYPE
    SYNTAX      Integer32
    MAX-ACCESS  read-write
    STATUS      current
    DESCRIPTION
           "The ACL rule destination port low limit."
    ::= { f3L2N2AAclRuleEntry 18 }

f3L2N2AAclRulePriority OBJECT-TYPE
    SYNTAX      Integer32
    MAX-ACCESS  read-write
    STATUS      current
    DESCRIPTION
           "The ACL rule priority."
    ::= { f3L2N2AAclRuleEntry 19 }

f3L2N2AAclRuleCOS OBJECT-TYPE
    SYNTAX      Integer32
    MAX-ACCESS  read-write
    STATUS      current
    DESCRIPTION
           "The ACL rule class of service."
    ::= { f3L2N2AAclRuleEntry 20 }

f3L2N2AAclRuleOperation OBJECT-TYPE
    SYNTAX      L3AclRuleOperation
    MAX-ACCESS  read-write
    STATUS      current
    DESCRIPTION
           "The ACL rule action."
    ::= { f3L2N2AAclRuleEntry 21 }

f3L2N2AAclRuleSummary OBJECT-TYPE
    SYNTAX      F3DisplayString
    MAX-ACCESS  read-only
    STATUS      current
    DESCRIPTION
           "The ACL rule summary."
    ::= { f3L2N2AAclRuleEntry 22 }

f3L2N2AAclRuleCosOverrideControl OBJECT-TYPE
    SYNTAX      TruthValue
    MAX-ACCESS  read-write
    STATUS      current
    DESCRIPTION
           "The ACL rule COS Override control."
    ::= { f3L2N2AAclRuleEntry 23 }

f3L2N2AAclRuleSrcMacAddressControl OBJECT-TYPE
    SYNTAX      TruthValue
    MAX-ACCESS  read-write
    STATUS      current
    DESCRIPTION
           "The ACL rule Source MAC address control."
    ::= { f3L2N2AAclRuleEntry 24 }

f3L2N2AAclRuleDynamicSrcMacAddressControl OBJECT-TYPE
    SYNTAX      TruthValue
    MAX-ACCESS  read-write
    STATUS      current
    DESCRIPTION
           "The ACL rule dynamic Source MAC address control."
    ::= { f3L2N2AAclRuleEntry 25 }

f3L2N2AAclRuleSrcMacAddress OBJECT-TYPE
    SYNTAX      MacAddress
    MAX-ACCESS  read-write
    STATUS      current
    DESCRIPTION
           "The ACL rule dynamic Source MAC address."
    ::= { f3L2N2AAclRuleEntry 26 }

f3L2N2AAclRuleSrcMacAddressMask OBJECT-TYPE
    SYNTAX      MacAddress
    MAX-ACCESS  read-write
    STATUS      current
    DESCRIPTION
           "The ACL rule dynamic Source MAC address mask."
    ::= { f3L2N2AAclRuleEntry 27 }

f3L2N2AAclRuleDstMacAddressControl OBJECT-TYPE
    SYNTAX      TruthValue
    MAX-ACCESS  read-write
    STATUS      current
    DESCRIPTION
           "The ACL rule dynamic Destination MAC address control."
    ::= { f3L2N2AAclRuleEntry 28 }

f3L2N2AAclRuleDstMacAddress OBJECT-TYPE
    SYNTAX      MacAddress
    MAX-ACCESS  read-write
    STATUS      current
    DESCRIPTION
           "The ACL rule dynamic Destination MAC address."
    ::= { f3L2N2AAclRuleEntry 29 }

f3L2N2AAclRuleDstMacAddressMask OBJECT-TYPE
    SYNTAX      MacAddress
    MAX-ACCESS  read-write
    STATUS      current
    DESCRIPTION
           "The ACL rule dynamic Destination MAC address mask."
    ::= { f3L2N2AAclRuleEntry 30 }

f3L2N2AAclRuleOuterVlanVIDControl OBJECT-TYPE
    SYNTAX      TruthValue
    MAX-ACCESS  read-write
    STATUS      current
    DESCRIPTION
           "The ACL rule outer VID control."
    ::= { f3L2N2AAclRuleEntry 31 }

f3L2N2AAclRuleOuterVlanVIDLowLimit OBJECT-TYPE
    SYNTAX      VlanId
    MAX-ACCESS  read-write
    STATUS      current
    DESCRIPTION
           "The ACL rule outer Vlan ID low limit."
    ::= { f3L2N2AAclRuleEntry 32 }

f3L2N2AAclRuleOuterVlanVIDHighLimit OBJECT-TYPE
    SYNTAX      VlanId
    MAX-ACCESS  read-write
    STATUS      current
    DESCRIPTION
           "The ACL rule outer Vlan ID high limit."
    ::= { f3L2N2AAclRuleEntry 33 }

f3L2N2AAclRuleInnerVlanVIDControl OBJECT-TYPE
    SYNTAX      TruthValue
    MAX-ACCESS  read-write
    STATUS      current
    DESCRIPTION
           "The ACL rule inner VID control."
    ::= { f3L2N2AAclRuleEntry 34 }

f3L2N2AAclRuleInnerVlanVIDLowLimit OBJECT-TYPE
    SYNTAX      VlanId
    MAX-ACCESS  read-write
    STATUS      current
    DESCRIPTION
           "The ACL rule inner Vlan ID low limit."
    ::= { f3L2N2AAclRuleEntry 35 }

f3L2N2AAclRuleInnerVlanVIDHighLimit OBJECT-TYPE
    SYNTAX      VlanId
    MAX-ACCESS  read-write
    STATUS      current
    DESCRIPTION
           "The ACL rule Inner Vlan ID high limit."
    ::= { f3L2N2AAclRuleEntry 36 }

f3L2N2AAclRuleOuterVlanPcpControl OBJECT-TYPE
    SYNTAX      TruthValue
    MAX-ACCESS  read-write
    STATUS      current
    DESCRIPTION
           "The ACL rule outer vlan PCP control."
    ::= { f3L2N2AAclRuleEntry 37 }

f3L2N2AAclRuleOuterVlanPcpLowLimit OBJECT-TYPE
    SYNTAX      VlanPriority
    MAX-ACCESS  read-write
    STATUS      current
    DESCRIPTION
           "The ACL rule outer vlan PCP priority low limit."
    ::= { f3L2N2AAclRuleEntry 38 }

f3L2N2AAclRuleOuterVlanPcpHighLimit OBJECT-TYPE
    SYNTAX      VlanPriority
    MAX-ACCESS  read-write
    STATUS      current
    DESCRIPTION
           "The ACL rule outer vlan PCP priority high limit."
    ::= { f3L2N2AAclRuleEntry 39 }

f3L2N2AAclRuleInnerVlanPcpControl OBJECT-TYPE
    SYNTAX      TruthValue
    MAX-ACCESS  read-write
    STATUS      current
    DESCRIPTION
           "The ACL rule inner vlan PCP control."
    ::= { f3L2N2AAclRuleEntry 40 }

f3L2N2AAclRuleInnerVlanPcpLowLimit OBJECT-TYPE
    SYNTAX      VlanPriority
    MAX-ACCESS  read-write
    STATUS      current
    DESCRIPTION
           "The ACL rule inner vlan PCP priority low limit."
    ::= { f3L2N2AAclRuleEntry 41 }

f3L2N2AAclRuleInnerVlanPcpHighLimit OBJECT-TYPE
    SYNTAX      VlanPriority
    MAX-ACCESS  read-write
    STATUS      current
    DESCRIPTION
           "The ACL rule inner vlan PCP priority high limit."
    ::= { f3L2N2AAclRuleEntry 42 }

f3L2N2AAclRuleOuterVlanDeiControl OBJECT-TYPE
    SYNTAX      TruthValue
    MAX-ACCESS  read-write
    STATUS      current
    DESCRIPTION
           "The ACL rule outer vlan DEI control."
    ::= { f3L2N2AAclRuleEntry 43 }

f3L2N2AAclRuleOuterVlanDei OBJECT-TYPE
    SYNTAX      Unsigned32 (0..1)
    MAX-ACCESS  read-write
    STATUS      current
    DESCRIPTION
           "The ACL rule outer vlan DEI."
    ::= { f3L2N2AAclRuleEntry 44 }

f3L2N2AAclRuleEtherTypeControl OBJECT-TYPE
    SYNTAX      TruthValue
    MAX-ACCESS  read-write
    STATUS      current
    DESCRIPTION
           "The ACL rule outer vlan ether type control."
    ::= { f3L2N2AAclRuleEntry 45 }

f3L2N2AAclRuleEtherType OBJECT-TYPE
    SYNTAX      Integer32
    MAX-ACCESS  read-write
    STATUS      current
    DESCRIPTION
           "The ACL rule outer vlan ether type."
    ::= { f3L2N2AAclRuleEntry 46 }

f3L2N2AAclRuleTcpFlagsControl OBJECT-TYPE
    SYNTAX      TruthValue
    MAX-ACCESS  read-write
    STATUS      current
    DESCRIPTION
           "The ACL rule outer vlan TCP flags control."
    ::= { f3L2N2AAclRuleEntry 47 }

f3L2N2AAclRuleTcpFlags OBJECT-TYPE
    SYNTAX      Integer32
    MAX-ACCESS  read-write
    STATUS      current
    DESCRIPTION
           "The ACL rule outer vlan TCP flags."
    ::= { f3L2N2AAclRuleEntry 48 }

f3L2N2AAclRuleSrcIpv4AddressHighLimit OBJECT-TYPE
    SYNTAX      IpAddress
    MAX-ACCESS  read-write
    STATUS      current
    DESCRIPTION
           "The ACL rule source ipv4 adress high limit."
    ::= { f3L2N2AAclRuleEntry 49 }

f3L2N2AAclRuleDstIpv4AddressHighLimit OBJECT-TYPE
    SYNTAX      IpAddress
    MAX-ACCESS  read-write
    STATUS      current
    DESCRIPTION
           "The ACL rule destination ipv4 adress high limit."
    ::= { f3L2N2AAclRuleEntry 50 }

f3L2N2AAclRuleIpv4PriorityHighLimit OBJECT-TYPE
    SYNTAX      Integer32
    MAX-ACCESS  read-write
    STATUS      current
    DESCRIPTION
           "The ACL rule ipv4 priority high limit."
    ::= { f3L2N2AAclRuleEntry 51 }

f3L2N2AAclRuleStorageType OBJECT-TYPE
    SYNTAX      StorageType
    MAX-ACCESS  read-create
    STATUS      current
    DESCRIPTION
           "The type of storage configured for this entry."
    ::= { f3L2N2AAclRuleEntry 52 }

f3L2N2AAclRuleRowStatus OBJECT-TYPE
    SYNTAX      RowStatus
    MAX-ACCESS  read-create
    STATUS      current
    DESCRIPTION
           "The status of this row.
          	An entry MUST NOT exist in the active state unless all
          	objects in the entry have an appropriate value, as described
          	in the description clause for each writable object.
 	
          	The values of f3L2N2AAclRuleRowStatus supported are
          	createAndGo(4) and destroy(6).  All mandatory attributes
          	must be specified in a single SNMP SET request with
          	f3L2N2AAclRuleRowStatus value as createAndGo(4).
          	Upon successful row creation, this object has a
          	value of active(1).
 	
          	The f3L2N2AAclRuleRowStatus object may be modified if
          	the associated instance of this object is equal to active(1)."
    ::= { f3L2N2AAclRuleEntry 53 }

f3L2N2AAclRuleAdminState OBJECT-TYPE
    SYNTAX      AdminState
    MAX-ACCESS  read-write
    STATUS      current
    DESCRIPTION
           "This object allows user configure the Acl Rule in-service or management state."
    ::= { f3L2N2AAclRuleEntry 54 }

f3L2N2AAclRuleActive OBJECT-TYPE
    SYNTAX      TruthValue
    MAX-ACCESS  read-write
    STATUS      current
    DESCRIPTION
           "The ACL rule active control."
    ::= { f3L2N2AAclRuleEntry 55 }

f3L2N2AAclRuleSrcIpV6AddressControl OBJECT-TYPE
    SYNTAX      TruthValue
    MAX-ACCESS  read-write
    STATUS      current
    DESCRIPTION
           "The ACL rule source ipv6 adress control."
    ::= { f3L2N2AAclRuleEntry 56 }

f3L2N2AAclRuleSrcIpV6Address OBJECT-TYPE
    SYNTAX      Ipv6Address
    MAX-ACCESS  read-write
    STATUS      current
    DESCRIPTION
           "The ACL rule source ipv6 adress."
    ::= { f3L2N2AAclRuleEntry 57 }

f3L2N2AAclRuleSrcIpV6AddressPrefixLen OBJECT-TYPE
    SYNTAX      Integer32
    MAX-ACCESS  read-write
    STATUS      current
    DESCRIPTION
           "The ACL rule source ipv6 adress prefix length."
    ::= { f3L2N2AAclRuleEntry 58 }

f3L2N2AAclRuleDstIpV6AddressControl OBJECT-TYPE
    SYNTAX      TruthValue
    MAX-ACCESS  read-write
    STATUS      current
    DESCRIPTION
           "The ACL rule destination ipv6 adress control."
    ::= { f3L2N2AAclRuleEntry 59 }

f3L2N2AAclRuleDstIpV6Address OBJECT-TYPE
    SYNTAX      Ipv6Address
    MAX-ACCESS  read-write
    STATUS      current
    DESCRIPTION
           "The ACL rule destination ipv6 adress."
    ::= { f3L2N2AAclRuleEntry 60 }

f3L2N2AAclRuleDstIpV6AddressPrefixLen OBJECT-TYPE
    SYNTAX      Integer32
    MAX-ACCESS  read-write
    STATUS      current
    DESCRIPTION
           "The ACL rule destination ipv6 adress prefix length."
    ::= { f3L2N2AAclRuleEntry 61 }

f3L2N2AAclRuleIpV6FlowLabelControl OBJECT-TYPE
    SYNTAX      TruthValue
    MAX-ACCESS  read-write
    STATUS      current
    DESCRIPTION
           "The ACL rule IPv6 flow lable control."
    ::= { f3L2N2AAclRuleEntry 62 }

f3L2N2AAclRuleIpV6FlowLabel OBJECT-TYPE
    SYNTAX      Integer32
    MAX-ACCESS  read-write
    STATUS      current
    DESCRIPTION
           "The ACL rule IPv6 flow lable."
    ::= { f3L2N2AAclRuleEntry 63 }


--
--L3 Policer. Used by Ge11x product
--
f3L3QosPolicerTable  OBJECT-TYPE
    SYNTAX      SEQUENCE OF F3L3QosPolicerEntry
    MAX-ACCESS  not-accessible
    STATUS      current
    DESCRIPTION
        "A list of entries corresponding to Ethernet Quality of Service 
         Policer for configuration purposes."
    ::= { f3L3Objects 7 }

f3L3QosPolicerEntry OBJECT-TYPE
    SYNTAX      F3L3QosPolicerEntry 
    MAX-ACCESS  not-accessible
    STATUS      current
    DESCRIPTION
         "A conceptual row in the f3L3QosPolicerTable. 
          These entries represent a Quality of Service Policer."
    INDEX { neIndex, shelfIndex, slotIndex, f3L3FlowPointPortTypeIndex, 
            f3L3FlowPointPortIndex, f3L3FlowPointIndex, f3L3QosPolicerIndex }
    ::= { f3L3QosPolicerTable 1 }

F3L3QosPolicerEntry ::= SEQUENCE {
    f3L3QosPolicerIndex                 Integer32,

    -- State Management params
    f3L3QosPolicerAdminState            AdminState,
    f3L3QosPolicerOperationalState      OperationalState,
    f3L3QosPolicerSecondaryState        SecondaryState,

    f3L3QosPolicerCIRLo                 Unsigned32,
    f3L3QosPolicerCIRHi                 Unsigned32,
    f3L3QosPolicerEIRLo                 Unsigned32,
    f3L3QosPolicerEIRHi                 Unsigned32,
    f3L3QosPolicerCBS                   Integer32,
    f3L3QosPolicerEBS                   Integer32,
    f3L3QosPolicerAlgorithm             PolicerAlgorithmType,
    f3L3QosPolicerColorMode             PolicerColorMode,
    f3L3QosPolicerCouplingFlag          TruthValue,
    f3L3QosPolicerStorageType           StorageType,
    f3L3QosPolicerRowStatus             RowStatus ,
    f3L3QosPolicerCIRMaxHi              Unsigned32,
    f3L3QosPolicerCIRMaxLo              Unsigned32,
    f3L3QosPolicerEIRMaxHi              Unsigned32,
    f3L3QosPolicerEIRMaxLo              Unsigned32,
    f3L3QosPolicerEnvelopeObject        VariablePointer,
    f3L3QosPolicerRank                  Integer32,
    f3L3QosPolicerPolicingEnabled       TruthValue
}

f3L3QosPolicerIndex OBJECT-TYPE
    SYNTAX      Integer32 (1..16)
    MAX-ACCESS  read-create
    STATUS      current
    DESCRIPTION
            "The Policer Index that represents the COS level.  This
             is applicable in case of a Multi COS flow. Index 1
             represents COS 0; Index 2 represents COS 1 and so on. 

             In release 5.6CC the range is extended to 1..16 to support duplicate
             N2A policers on a Flow. The duplicate policers are created under a Flow 
             if network interface of the Flow is ERP Group or Split Horizon Group. 
             In case of multi-cos Flow indices 1..8 represent policers of COS 0..7 
             going from Network 1 port; indices 9..16 represent policers for COS 0..7 
             going from Network 2 port.
             In case of single-cos Flow index 1 represents policer going from Network 1
             port; index 9 represents policer going from Network 2 port.
             "
    ::= { f3L3QosPolicerEntry 1 }

-- State Management params
f3L3QosPolicerAdminState OBJECT-TYPE
    SYNTAX      AdminState 
    MAX-ACCESS  read-write
    STATUS      current
    DESCRIPTION
            "This object represents the Administrative State of 
             the QOS Flow Policer." 
    ::= { f3L3QosPolicerEntry 2 }

f3L3QosPolicerOperationalState OBJECT-TYPE
    SYNTAX      OperationalState 
    MAX-ACCESS  read-only
    STATUS      current
    DESCRIPTION
            "This object represents the Operational State of the QOS Flow Policer." 
    ::= { f3L3QosPolicerEntry 3 }

f3L3QosPolicerSecondaryState OBJECT-TYPE
    SYNTAX      SecondaryState 
    MAX-ACCESS  read-only
    STATUS      current
    DESCRIPTION
            "This object represents the Secondary State of the QOS Flow Policer." 
    ::= { f3L3QosPolicerEntry 4 }

f3L3QosPolicerCIRLo OBJECT-TYPE
    SYNTAX     Unsigned32
    MAX-ACCESS read-create
    STATUS     current
    DESCRIPTION
         "This object allows specification of the Commited Information
          Rate(CIR) on Policer.  This represents the lower 32 bits of the
          CIR."
     ::= { f3L3QosPolicerEntry 5 }

f3L3QosPolicerCIRHi OBJECT-TYPE
    SYNTAX     Unsigned32
    MAX-ACCESS read-create
    STATUS     current
    DESCRIPTION
         "This object allows specification of the Commited Information
          Rate(CIR) on Policer.  This represents the upper 32 bits of the
          CIR."
     ::= { f3L3QosPolicerEntry 6 }

f3L3QosPolicerEIRLo OBJECT-TYPE
    SYNTAX     Unsigned32
    MAX-ACCESS read-create
    STATUS     current
    DESCRIPTION
         "This object allows specification of the Excess Information
          Rate(EIR) on the Policer.  This represents the lower 32 bits
          of the EIR."
     ::= { f3L3QosPolicerEntry 7 }

f3L3QosPolicerEIRHi OBJECT-TYPE
    SYNTAX     Unsigned32
    MAX-ACCESS read-create
    STATUS     current
    DESCRIPTION
         "This object allows specification of the Excess Information
          Rate(EIR) on the Policer.  This represents the upper 32 bits
          of the EIR."
     ::= { f3L3QosPolicerEntry 8 }

f3L3QosPolicerCBS OBJECT-TYPE
    SYNTAX     Integer32
    MAX-ACCESS read-create
    STATUS     current
    DESCRIPTION
         "This object allows specification of the Commited Burst Size
          (CBS) on Policer."
     ::= { f3L3QosPolicerEntry 9 }

f3L3QosPolicerEBS OBJECT-TYPE
    SYNTAX     Integer32
    MAX-ACCESS read-create
    STATUS     current
    DESCRIPTION
         "This object allows specification of the Excess Burst Size
          (EBS) on the Policer."
     ::= { f3L3QosPolicerEntry 10 }

f3L3QosPolicerAlgorithm OBJECT-TYPE
    SYNTAX      PolicerAlgorithmType 
    MAX-ACCESS  read-only
    STATUS      current
    DESCRIPTION
          "This object allows specification of Policer algorithm as
           'srTCM' (Single Rate Triple Color Marking) or 'trTCM' (Two Rate
           Triple Color Marking)."
    ::= { f3L3QosPolicerEntry 11 }

f3L3QosPolicerColorMode OBJECT-TYPE
    SYNTAX      PolicerColorMode 
    MAX-ACCESS  read-create
    STATUS      current
    DESCRIPTION
          "This object allows specification of Policer Color Mode as
           'color-aware' or 'color-blind'."
    ::= { f3L3QosPolicerEntry 12 }

f3L3QosPolicerCouplingFlag OBJECT-TYPE
    SYNTAX      TruthValue
    MAX-ACCESS  read-create
    STATUS      current
    DESCRIPTION
       "This object allows specification of Policer Coupling Flag.
        When coupling is enabled, tokens that would normally be 
        added to the C-bucket are passed to the E-bucket only once the CIR
        bucket has reached its CBS level. Therefore under this condition
        the E-bucket is being filled at the rate of CIR + EIR. 
        Normally the long term average of frames declared yellow is 
        bounded by the EIR. Coupling is a function to allow the 
        long term average of frames declared yellow to be bounded by 
        CIR + EIR. This allows a higher volume of yellow frames 
        to be delivered/received if the arrival of green marked frames 
        is low.  Tokens from the E-bucket do NOT get passed to the 
        C-bucket once the EBS level has been reached.
        Enabling coupling in combination with a provisioned EIR of 0 
        allows for a single rate three color marking (srTCM) algorithm 
        to be established.  In this situation the E-bucket is filled at the 
        CIR rate in the case the C-bucket is filled to its CBS level."
    ::= { f3L3QosPolicerEntry 13 }

f3L3QosPolicerStorageType OBJECT-TYPE
    SYNTAX     StorageType
    MAX-ACCESS read-create
    STATUS     current
    DESCRIPTION
            "The type of storage configured for this entry."
    ::= { f3L3QosPolicerEntry 14 }

f3L3QosPolicerRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of f3L3QosPolicerRowStatus supported are
            createAndGo(4) and destroy(6).  All mandatory attributes
            must be specified in a single SNMP SET request with
            f3L3QosPolicerRowStatus value as createAndGo(4).
            Upon successful row creation, this object has a
            value of active(1).

            The f3L3QosPolicerRowStatus object may be modified if
            the associated instance of this object is equal to active(1)."
    ::= { f3L3QosPolicerEntry 15 }

f3L3QosPolicerCIRMaxHi OBJECT-TYPE
    SYNTAX     Unsigned32
    MAX-ACCESS read-write
    STATUS     current
    DESCRIPTION
         "This object allows specification of the Commited Information
          Rate(CIR) MAX on Policer.  This represents the high 32 bits."
     ::= { f3L3QosPolicerEntry 16 }

f3L3QosPolicerCIRMaxLo OBJECT-TYPE
    SYNTAX     Unsigned32
    MAX-ACCESS read-write
    STATUS     current
    DESCRIPTION
         "This object allows specification of the Commited Information
          Rate(CIR) MAX on Policer.  This represents the lower 32 bits."
     ::= { f3L3QosPolicerEntry 17 }

f3L3QosPolicerEIRMaxHi OBJECT-TYPE
    SYNTAX     Unsigned32
    MAX-ACCESS read-write
    STATUS     current
    DESCRIPTION
         "This object allows specification of the Excess Information
          Rate(EIR) MAX on the Policer.  This represents the high 32 bits."
     ::= { f3L3QosPolicerEntry 18 }

f3L3QosPolicerEIRMaxLo OBJECT-TYPE
    SYNTAX     Unsigned32
    MAX-ACCESS read-write
    STATUS     current
    DESCRIPTION
         "This object allows specification of the Excess Information
          Rate(EIR) MAX on the Policer.  This represents the lower 32 bits."
     ::= { f3L3QosPolicerEntry 19 }

f3L3QosPolicerEnvelopeObject OBJECT-TYPE
    SYNTAX     VariablePointer
    MAX-ACCESS read-write
    STATUS     current
    DESCRIPTION
         "This object allows specification of envelope object."
     ::= { f3L3QosPolicerEntry 20 }

f3L3QosPolicerRank OBJECT-TYPE
    SYNTAX     Integer32
    MAX-ACCESS read-write
    STATUS     current
    DESCRIPTION
         "This object allows specification of rank value."
     ::= { f3L3QosPolicerEntry 21 }

f3L3QosPolicerPolicingEnabled OBJECT-TYPE
    SYNTAX     TruthValue
    MAX-ACCESS read-write
    STATUS     current
    DESCRIPTION
         "This object describes whether the policing is enabled."
     ::= { f3L3QosPolicerEntry 22 }


--
--  L3 Port Quality of Service Shaper 
--
f3L3QosShaperTable  OBJECT-TYPE
    SYNTAX      SEQUENCE OF F3L3QosShaperEntry
    MAX-ACCESS  not-accessible
    STATUS      current
    DESCRIPTION
            "A list of entries corresponding to Ethernet Access Port 
             Quality of Service Shaper for configuration purposes.
             These shapers can be managed when the Access Port is
             in evpl mode and are relevant for traffic in the
             network to access direction."
    ::= { f3L3Objects 8 }

f3L3QosShaperEntry OBJECT-TYPE
    SYNTAX      F3L3QosShaperEntry 
    MAX-ACCESS  not-accessible
    STATUS      current
    DESCRIPTION
            "A conceptual row in the f3L3QosShaperTable. 
             These entries represent a Quality of Service Shaper."
    INDEX { neIndex, shelfIndex, slotIndex, f3L3FlowPointPortTypeIndex, 
            f3L3FlowPointPortIndex, f3L3FlowPointIndex,  
            f3L3QosShaperIndex }
    ::= { f3L3QosShaperTable 1 }

F3L3QosShaperEntry ::= SEQUENCE {
    -- QOS Shaper Index/Id
    f3L3QosShaperIndex               Integer32,

    -- State Management params
    f3L3QosShaperAdminState          AdminState,
    f3L3QosShaperOperationalState    OperationalState,
    f3L3QosShaperSecondaryState      SecondaryState,

    -- QOS Shaper Properties
    f3L3QosShaperCIRLo               Unsigned32,
    f3L3QosShaperCIRHi               Unsigned32,
    f3L3QosShaperEIRLo               Unsigned32,
    f3L3QosShaperEIRHi               Unsigned32,
    f3L3QosShaperBufferSize          Unsigned32,
    f3L3QosShaperCOS                 Integer32,

    --wred threshold
    f3L3QosShaperWredGreenMinQueueThreshold       Unsigned32,
    f3L3QosShaperWredGreenMaxQueueThreshold       Unsigned32,
    f3L3QosShaperWredGreenDropProbability         Unsigned32,
    f3L3QosShaperWredYellowMinQueueThreshold      Unsigned32,
    f3L3QosShaperWredYellowMaxQueueThreshold      Unsigned32,
    f3L3QosShaperWredYellowDropProbability        Unsigned32,
    f3L3QosShaperStorageType                      StorageType,
    f3L3QosShaperRowStatus                        RowStatus,
    f3L3QosShaperWfqWeight                        Integer32
}

f3L3QosShaperIndex OBJECT-TYPE
    SYNTAX      Integer32 (1..8)
    MAX-ACCESS  read-create
    STATUS      current
    DESCRIPTION
            "The unique integer index value corresponding to a 
             Quality of Service Shaper."
    ::= { f3L3QosShaperEntry 1 }

-- State Management params
f3L3QosShaperAdminState OBJECT-TYPE
    SYNTAX      AdminState 
    MAX-ACCESS  read-write
    STATUS      current
    DESCRIPTION
            "This object represents the Administrative State of 
             the QOS Shaper." 
    ::= { f3L3QosShaperEntry 2 }

f3L3QosShaperOperationalState OBJECT-TYPE
    SYNTAX      OperationalState 
    MAX-ACCESS  read-only
    STATUS      current
    DESCRIPTION
            "This object represents the Operational State of the QOS Shaper." 
    ::= { f3L3QosShaperEntry 3 }

f3L3QosShaperSecondaryState OBJECT-TYPE
    SYNTAX      SecondaryState 
    MAX-ACCESS  read-only
    STATUS      current
    DESCRIPTION
            "This object represents the Secondary State of the QOS Shaper." 
    ::= { f3L3QosShaperEntry 4 }

f3L3QosShaperCIRLo OBJECT-TYPE
    SYNTAX     Unsigned32
    MAX-ACCESS read-create
    STATUS     current
    DESCRIPTION
         "This object represents the Commited Information
          Rate(CIR) (Lower 32 bits)of a Shaper."
     ::= { f3L3QosShaperEntry 5 }

f3L3QosShaperCIRHi OBJECT-TYPE
    SYNTAX     Unsigned32
    MAX-ACCESS read-create
    STATUS     current
    DESCRIPTION
         "This object represents the Commited Information
          Rate(CIR) (Higher 32 bits) of a Shaper."
     ::= { f3L3QosShaperEntry 6 }

f3L3QosShaperEIRLo OBJECT-TYPE
    SYNTAX     Unsigned32
    MAX-ACCESS read-create
    STATUS     current
    DESCRIPTION
         "This object represents the Excess Information
          Rate(EIR) (Higher 32 bits) on the Shaper."
     ::= { f3L3QosShaperEntry 7 }

f3L3QosShaperEIRHi OBJECT-TYPE
    SYNTAX     Unsigned32
    MAX-ACCESS read-create
    STATUS     current
    DESCRIPTION
         "This object represents the Excess Information
          Rate(EIR) (Higher 32 bits) on the Shaper."
     ::= { f3L3QosShaperEntry 8 }

f3L3QosShaperBufferSize OBJECT-TYPE
    SYNTAX     Unsigned32
    MAX-ACCESS read-create
    STATUS     current
    DESCRIPTION
         "This object represents the Buffer Size of the Shaper."
     ::= { f3L3QosShaperEntry 9 }

f3L3QosShaperCOS OBJECT-TYPE
    SYNTAX     Integer32 (0..7)
    MAX-ACCESS read-only
    STATUS     current
    DESCRIPTION
            "This object provides the COS (Class of Service)
             value for the QOS Shaper."
    ::= { f3L3QosShaperEntry 10 }

f3L3QosShaperWredGreenMinQueueThreshold OBJECT-TYPE
    SYNTAX     Unsigned32
    MAX-ACCESS read-create
    STATUS     current
    DESCRIPTION
         "This object represents the Wred green packet min queue threshold value."
     ::= { f3L3QosShaperEntry 11 }

f3L3QosShaperWredGreenMaxQueueThreshold OBJECT-TYPE
    SYNTAX     Unsigned32
    MAX-ACCESS read-create
    STATUS     current
    DESCRIPTION
         "This object represents the Wred green packet max queue threshold value."
     ::= { f3L3QosShaperEntry 12 }

f3L3QosShaperWredGreenDropProbability OBJECT-TYPE
    SYNTAX     Unsigned32
    MAX-ACCESS read-create
    STATUS     current
    DESCRIPTION
         "This object represents the Wred green packet drop probability."
     ::= { f3L3QosShaperEntry 13 }

f3L3QosShaperWredYellowMinQueueThreshold OBJECT-TYPE
    SYNTAX     Unsigned32
    MAX-ACCESS read-create
    STATUS     current
    DESCRIPTION
         "This object represents the Wred yellow packet min queue threshold value."
     ::= { f3L3QosShaperEntry 14 }

f3L3QosShaperWredYellowMaxQueueThreshold OBJECT-TYPE
    SYNTAX     Unsigned32
    MAX-ACCESS read-create
    STATUS     current
    DESCRIPTION
         "This object represents the Wred yellow packet max queue threshold value."
     ::= { f3L3QosShaperEntry 15 }

f3L3QosShaperWredYellowDropProbability OBJECT-TYPE
    SYNTAX     Unsigned32
    MAX-ACCESS read-create
    STATUS     current
    DESCRIPTION
         "This object represents the Wred yellow packet drop probability."
     ::= { f3L3QosShaperEntry 16 }

f3L3QosShaperStorageType OBJECT-TYPE
    SYNTAX     StorageType
    MAX-ACCESS read-create
    STATUS     current
    DESCRIPTION
            "The type of storage configured for this entry."
    ::= { f3L3QosShaperEntry 17 }

f3L3QosShaperRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of f3L3QosShaperRowStatus supported are
            createAndGo(4) and destroy(6).  All mandatory attributes
            must be specified in a single SNMP SET request with
            f3L3QosShaperRowStatus value as createAndGo(4).
            Upon successful row creation, this object has a
            value of active(1).

            The f3L3QosShaperRowStatus object may be modified if
            the associated instance of this object is equal to active(1)."
    ::= { f3L3QosShaperEntry 18 }

f3L3QosShaperWfqWeight OBJECT-TYPE
    SYNTAX     Integer32
    MAX-ACCESS read-write
    STATUS     current
    DESCRIPTION
         "This object represents wfq weight value."
     ::= { f3L3QosShaperEntry 19 }

--
--  L3 traffic ip interface Table
--
f3L3TrafficIPInterfaceTable  OBJECT-TYPE
    SYNTAX      SEQUENCE OF F3L3TrafficIPInterfaceEntry
    MAX-ACCESS  not-accessible
    STATUS      current
    DESCRIPTION
            "A list of entries for the L3 Traffic IP Interface."
    ::= { f3L3Objects 9 }

f3L3TrafficIPInterfaceEntry  OBJECT-TYPE
    SYNTAX      F3L3TrafficIPInterfaceEntry
    MAX-ACCESS  not-accessible
    STATUS      current
    DESCRIPTION
            "A conceptual row in the f3L3TrafficIPInterfaceTable."
    INDEX { neIndex, shelfIndex, slotIndex,
            f3L3FlowPointPortIndex, f3L3FlowPointIndex, f3L3TrafficIPIfIndex }
    ::= { f3L3TrafficIPInterfaceTable 1 }

F3L3TrafficIPInterfaceEntry ::= SEQUENCE {
    f3L3TrafficIPIfIndex                               Integer32,
    f3L3TrafficIPIfName                                DisplayString,
    f3L3TrafficIPIfAdminState                          AdminState,
    f3L3TrafficIPIfSecondaryState                      SecondaryState,
    f3L3TrafficIPIfOperationalState                    OperationalState,
    f3L3TrafficIPIfProxyArpEnabled                     TruthValue,
    f3L3TrafficIPIfIpAddressSourceType                 IfIpAddressSourceType, 
    f3L3TrafficIPIfMgmtUseEnable                       TruthValue,
    f3L3TrafficIPIfIpAddress                           IpAddress,
    f3L3TrafficIPIfMask                                IpAddress,

    f3L3TrafficIPIfDhcpRelayInterfaceSide              DhcpRelayInterfaceSide,
    f3L3TrafficIPIfDhcpRelayVendorClassiDOpt60         DisplayString,
    f3L3TrafficIPIfDhcpRelayVendorClassiDOpt60Control  TruthValue,
    f3L3TrafficIPIfDhcpRelayUserClassOpt77             DisplayString,
    f3L3TrafficIPIfDhcpRelayUserClassOpt77Control      TruthValue,
    f3L3TrafficIPIfDhcpRelayInfoOpt82Sub1              DisplayString,
    f3L3TrafficIPIfDhcpRelayInfoOpt82Sub1Enabled       TruthValue,
    f3L3TrafficIPIfDhcpRelayInfoOpt82Sub2              DisplayString,
    f3L3TrafficIPIfDhcpRelayInfoOpt82Sub2Enabled       TruthValue,

    f3L3TrafficIPIfDhcpEnabled                         TruthValue,
    f3L3TrafficIPIfDhcpRole                            CmDhcpRole,
    f3L3TrafficIPIfDhcpClientIdEnabled                 TruthValue,
    f3L3TrafficIPIfDhcpClientId                        DisplayString,
    f3L3TrafficIPIfDhcpClassIdEnabled                  TruthValue,
    f3L3TrafficIPIfDhcpHostNameEnabled                 TruthValue,
    f3L3TrafficIPIfDhcpHostName                        DisplayString,
    f3L3TrafficIPIfDhcpClientIdType                    DHCPCIDType,
    f3L3TrafficIPIfDhcpHostNameType                    DHCPHostNameType,
    f3L3TrafficIPIfStorageType                         StorageType,
    f3L3TrafficIPIfRowStatus                           RowStatus,
    f3L3TrafficIPIfAction                              AffectiveArpActionType,
    f3L3TrafficIPIfActionX                             TrafficIpInterfaceActionType,
    f3L3TrafficIPIfUnnumberedControl                   TruthValue,
    f3L3TrafficIPIfBorrowedIntf                        DisplayString,
    
    f3L3TrafficIPIfIpMode                              IpMode,
    f3L3TrafficIPIfType                                IpInterfaceType,
    f3L3TrafficIPIfIpv6LinkLocalAddr                   Ipv6Address,
    f3L3TrafficIPIfIpv6LinkLocalAddrMode               Ipv6LinkLocalAddressMode,
    f3L3TrafficIPIfIpv6StatelessAddrAutoconfigEnabled  TruthValue,
    f3L3TrafficIPIfDefaultGateway                      Ipv6Address,
    f3L3TrafficIPIfIcmpErrorMsgRateLimit               Integer32,
    f3L3TrafficIPIfDhcpv6Role                          CmDhcpRole,
    f3L3TrafficIPIfDhcpv6Enabled                       TruthValue,
    f3L3TrafficIPIfDhcpRapidCommitControlEnabled       TruthValue,
    f3L3TrafficIPIfMaxRAInterval                       Unsigned32,
    f3L3TrafficIPIfMinRAInterval                       Unsigned32,
    f3L3TrafficIPIfRouterLifeTime                      Unsigned32,
    f3L3TrafficIPIfReachableTime                       Unsigned32,
    f3L3TrafficIPIfRaDhcpMoreConfigEnabled             TruthValue,
    f3L3TrafficIPIfRaManagedAddressConfigEnabled       TruthValue,
    f3L3TrafficIPIfRaRDNSSOptionEnabled                TruthValue,
    f3L3TrafficIPIfRaRDNSSLifeTime                     Unsigned32,
    f3L3TrafficIPIfRaDNSSList                          DisplayString,
    f3L3TrafficIPIfRaDefaultRouterPreference           NdpRaDefaultRouterPreference,
    f3L3TrafficIPIfDupAddrDetectControl                TruthValue,
    f3L3TrafficIPIfDupAddrDetectTransmits              Unsigned32,
    f3L3TrafficIPIfDupAddrDetectRetransTimer           Unsigned32,
    f3L3TrafficIPIfMTU                                 Integer32
}

f3L3TrafficIPIfIndex OBJECT-TYPE
    SYNTAX      Integer32
    MAX-ACCESS  not-accessible
    STATUS      current
    DESCRIPTION
           "It specifies the traffic IP interface number."
    ::= { f3L3TrafficIPInterfaceEntry 1 }

f3L3TrafficIPIfName OBJECT-TYPE
    SYNTAX      DisplayString (SIZE (0..15))
    MAX-ACCESS  read-write
    STATUS      current
    DESCRIPTION
           "It specifies the traffic IP interface name."
    ::= { f3L3TrafficIPInterfaceEntry 2 }

f3L3TrafficIPIfAdminState OBJECT-TYPE
    SYNTAX      AdminState
    MAX-ACCESS  read-write
    STATUS      current
    DESCRIPTION
           "This object represents the Administrative State of the interface."
    ::= { f3L3TrafficIPInterfaceEntry 3 }

f3L3TrafficIPIfSecondaryState OBJECT-TYPE
    SYNTAX      SecondaryState
    MAX-ACCESS  read-only
    STATUS      current
    DESCRIPTION
           "This object represents the Secondary State of the interface."
    ::= { f3L3TrafficIPInterfaceEntry 4 }

f3L3TrafficIPIfOperationalState OBJECT-TYPE
    SYNTAX      OperationalState
    MAX-ACCESS  read-only
    STATUS      current
    DESCRIPTION
           "This object represents the Operational State of the interface."
    ::= { f3L3TrafficIPInterfaceEntry 5 }

f3L3TrafficIPIfProxyArpEnabled OBJECT-TYPE
    SYNTAX      TruthValue
    MAX-ACCESS  read-write
    STATUS      current
    DESCRIPTION
           "This attribute controls poxy ARP on this interface."
    ::= { f3L3TrafficIPInterfaceEntry 6 }

f3L3TrafficIPIfIpAddressSourceType OBJECT-TYPE
    SYNTAX      IfIpAddressSourceType
    MAX-ACCESS  read-write
    STATUS      current
    DESCRIPTION
           "This attribute represents the IP address source type."
    ::= { f3L3TrafficIPInterfaceEntry 7 }

f3L3TrafficIPIfMgmtUseEnable OBJECT-TYPE
    SYNTAX      TruthValue
    MAX-ACCESS  read-write
    STATUS      current
    DESCRIPTION
           "This attribute is used for controlling use of interface for management.
            If enabled the NE can be managed through this interface."
    ::= { f3L3TrafficIPInterfaceEntry 8 }

f3L3TrafficIPIfIpAddress OBJECT-TYPE
    SYNTAX      IpAddress
    MAX-ACCESS  read-write
    STATUS      current
    DESCRIPTION
           "IP Address of the interface."
    ::= { f3L3TrafficIPInterfaceEntry 9 }

f3L3TrafficIPIfMask OBJECT-TYPE
    SYNTAX      IpAddress
    MAX-ACCESS  read-write
    STATUS      current
    DESCRIPTION
           "IP Address mask of the interface."
    ::= { f3L3TrafficIPInterfaceEntry 10 }

f3L3TrafficIPIfDhcpRelayInterfaceSide OBJECT-TYPE
    SYNTAX      DhcpRelayInterfaceSide
    MAX-ACCESS  read-write
    STATUS      current
    DESCRIPTION
           "This object represents interface side."
    ::= { f3L3TrafficIPInterfaceEntry 11 }

f3L3TrafficIPIfDhcpRelayVendorClassiDOpt60 OBJECT-TYPE
    SYNTAX      DisplayString (SIZE (0..255))
    MAX-ACCESS  read-write
    STATUS      current
    DESCRIPTION
           "DHCP Option 60 value used for association of received
            DHCP message with Traffic IP Interface."

    ::= { f3L3TrafficIPInterfaceEntry 12 }

f3L3TrafficIPIfDhcpRelayVendorClassiDOpt60Control OBJECT-TYPE
    SYNTAX      TruthValue
    MAX-ACCESS  read-write
    STATUS      current
    DESCRIPTION
           "This Attribute is used to control inspection of 
           DHCP option 60 presence in the DHCP messages received 
           on Client Side Traffic IP Interface."

    ::= { f3L3TrafficIPInterfaceEntry 13 }

f3L3TrafficIPIfDhcpRelayUserClassOpt77 OBJECT-TYPE
    SYNTAX      DisplayString (SIZE (0..255))
    MAX-ACCESS  read-write
    STATUS      current
    DESCRIPTION
           "DHCP Option 77 value used for association of received
            DHCP message with Traffic IP Interface ."
    ::= { f3L3TrafficIPInterfaceEntry 14 }

f3L3TrafficIPIfDhcpRelayUserClassOpt77Control OBJECT-TYPE
    SYNTAX      TruthValue
    MAX-ACCESS  read-write
    STATUS      current
    DESCRIPTION
           "This Attribute is used to control inspection of 
           DHCP option 77 presence in the DHCP messages received 
           on Client Side Traffic IP Interface."

    ::= { f3L3TrafficIPInterfaceEntry 15 }

f3L3TrafficIPIfDhcpRelayInfoOpt82Sub1 OBJECT-TYPE
    SYNTAX      DisplayString (SIZE (0..255))
    MAX-ACCESS  read-write
    STATUS      current
    DESCRIPTION
           "DHCP Option 82 sub option 1 value."
    ::= { f3L3TrafficIPInterfaceEntry 16 }

f3L3TrafficIPIfDhcpRelayInfoOpt82Sub1Enabled OBJECT-TYPE
    SYNTAX      TruthValue
    MAX-ACCESS  read-write
    STATUS      current
    DESCRIPTION
           "This Attribute is used to control inspection of 
           DHCP option 82 sub option 1 presence in the DHCP messages received 
           on Client Side Traffic IP Interface."
    ::= { f3L3TrafficIPInterfaceEntry 17 }

f3L3TrafficIPIfDhcpRelayInfoOpt82Sub2 OBJECT-TYPE
    SYNTAX      DisplayString (SIZE (0..255))
    MAX-ACCESS  read-write
    STATUS      current
    DESCRIPTION
           "DHCP Option 82 sub option 2 value."
    ::= { f3L3TrafficIPInterfaceEntry 18 }

f3L3TrafficIPIfDhcpRelayInfoOpt82Sub2Enabled OBJECT-TYPE
    SYNTAX      TruthValue
    MAX-ACCESS  read-write
    STATUS      current
    DESCRIPTION
           "This Attribute is used to control inspection of 
           DHCP option 82 sub option 2 presence in the DHCP messages received 
           on Client Side Traffic IP Interface."
    ::= { f3L3TrafficIPInterfaceEntry 19 }

f3L3TrafficIPIfDhcpEnabled OBJECT-TYPE
    SYNTAX      TruthValue
    MAX-ACCESS  read-write
    STATUS      current
    DESCRIPTION
           "Whether or not DHCP is enabled on this interface."
    ::= { f3L3TrafficIPInterfaceEntry 20 }

f3L3TrafficIPIfDhcpRole OBJECT-TYPE
    SYNTAX      CmDhcpRole
    MAX-ACCESS  read-write
    STATUS      current
    DESCRIPTION
           "Specify the DHCP role on this interface."
    ::= { f3L3TrafficIPInterfaceEntry 21 }

f3L3TrafficIPIfDhcpClientIdEnabled OBJECT-TYPE
    SYNTAX      TruthValue
    MAX-ACCESS  read-write
    STATUS      current
    DESCRIPTION
           "Whether or not DHCP client id enabled."
    ::= { f3L3TrafficIPInterfaceEntry 22 }

f3L3TrafficIPIfDhcpClientId OBJECT-TYPE
    SYNTAX      DisplayString
    MAX-ACCESS  read-write
    STATUS      current
    DESCRIPTION
           "Specify the DHCP Cliend ID value."
    ::= { f3L3TrafficIPInterfaceEntry 23 }

f3L3TrafficIPIfDhcpClassIdEnabled OBJECT-TYPE
    SYNTAX      TruthValue
    MAX-ACCESS  read-write
    STATUS      current
    DESCRIPTION
           "Whether or not DHCP class id enabled."
    ::= { f3L3TrafficIPInterfaceEntry 24 }

f3L3TrafficIPIfDhcpHostNameEnabled OBJECT-TYPE
    SYNTAX      TruthValue
    MAX-ACCESS  read-write
    STATUS      current
    DESCRIPTION
           "Whether or not DHCP host name enabled."
    ::= { f3L3TrafficIPInterfaceEntry 25 }

f3L3TrafficIPIfDhcpHostName OBJECT-TYPE
    SYNTAX      DisplayString
    MAX-ACCESS  read-write
    STATUS      current
    DESCRIPTION
           "DHCP host name value."
    ::= { f3L3TrafficIPInterfaceEntry 26 }

f3L3TrafficIPIfDhcpClientIdType OBJECT-TYPE
    SYNTAX      DHCPCIDType
    MAX-ACCESS  read-write
    STATUS      current
    DESCRIPTION
           "This object describe whether the dhcp cid type."
    ::= { f3L3TrafficIPInterfaceEntry 27 }

f3L3TrafficIPIfDhcpHostNameType OBJECT-TYPE
    SYNTAX      DHCPHostNameType
    MAX-ACCESS  read-write
    STATUS      current
    DESCRIPTION
           "This object describe whether the dhcp host name type."
    ::= { f3L3TrafficIPInterfaceEntry 28 }

f3L3TrafficIPIfStorageType OBJECT-TYPE
    SYNTAX      StorageType
    MAX-ACCESS  read-create
    STATUS      current
    DESCRIPTION
           "The type of storage configured for this entry."
    ::= { f3L3TrafficIPInterfaceEntry 29 }

f3L3TrafficIPIfRowStatus OBJECT-TYPE
    SYNTAX      RowStatus
    MAX-ACCESS  read-create
    STATUS      current
    DESCRIPTION
           "The status of this row.
          	An entry MUST NOT exist in the active state unless all
          	objects in the entry have an appropriate value, as described
          	in the description clause for each writable object.
 	
          	The values of f3L3TrafficIPIfRowStatus supported are
          	createAndGo(4) and destroy(6).  All mandatory attributes
          	must be specified in a single SNMP SET request with
          	f3L3TrafficIPIfRowStatus value as createAndGo(4).
          	Upon successful row creation, this object has a
          	value of active(1).
 	
          	The f3L3TrafficIPIfRowStatus object may be modified if
          	the associated instance of this object is equal to active(1)."
    ::= { f3L3TrafficIPInterfaceEntry 30 }

f3L3TrafficIPIfAction OBJECT-TYPE
    SYNTAX      AffectiveArpActionType
    MAX-ACCESS  read-write
    STATUS      deprecated
    DESCRIPTION
           "This objects describes action set on this traffic ip interface.
            DEPRECATED and new variable to use is f3L3TrafficIPIfActionX."
    ::= { f3L3TrafficIPInterfaceEntry 31 }

f3L3TrafficIPIfActionX OBJECT-TYPE
    SYNTAX      TrafficIpInterfaceActionType
    MAX-ACCESS  read-write
    STATUS      current
    DESCRIPTION
           "This objects describes action set on this traffic ip interface."
    ::= { f3L3TrafficIPInterfaceEntry 32 }

f3L3TrafficIPIfUnnumberedControl OBJECT-TYPE
    SYNTAX  TruthValue
    MAX-ACCESS  read-create
    STATUS  current
    DESCRIPTION
        "This object specify IP interface whether is numbered."
    ::= { f3L3TrafficIPInterfaceEntry 33 }

f3L3TrafficIPIfBorrowedIntf OBJECT-TYPE
    SYNTAX  DisplayString
    MAX-ACCESS  read-create
    STATUS  current
    DESCRIPTION
        "This object specify IP interface name whose IP address
         is borrowed from currect object."
    ::= { f3L3TrafficIPInterfaceEntry 34 }

f3L3TrafficIPIfIpMode OBJECT-TYPE
    SYNTAX     IpMode 
    MAX-ACCESS read-write
    STATUS   current
    DESCRIPTION
       "This object means the ip mode for the interface."
    ::= { f3L3TrafficIPInterfaceEntry 35 }

f3L3TrafficIPIfType OBJECT-TYPE
    SYNTAX      IpInterfaceType
    MAX-ACCESS  read-write
    STATUS      current
    DESCRIPTION
           "This object represents the type of the interface."
    ::= { f3L3TrafficIPInterfaceEntry 36 }

f3L3TrafficIPIfIpv6LinkLocalAddr OBJECT-TYPE
    SYNTAX      Ipv6Address
    MAX-ACCESS  read-write
    STATUS      current
    DESCRIPTION
           "Link-local Address."
    ::= { f3L3TrafficIPInterfaceEntry 37 }

f3L3TrafficIPIfIpv6LinkLocalAddrMode OBJECT-TYPE
    SYNTAX      Ipv6LinkLocalAddressMode
    MAX-ACCESS  read-write
    STATUS      current
    DESCRIPTION
           "The assignment mode of IPv6 Link-Local Address, only manual and automatic are applicable."
    ::= { f3L3TrafficIPInterfaceEntry 38 }

f3L3TrafficIPIfIpv6StatelessAddrAutoconfigEnabled OBJECT-TYPE
    SYNTAX      TruthValue
    MAX-ACCESS  read-write
    STATUS      current
    DESCRIPTION
           "This is the control to enable or disable stateless
            address auto configuration."
    ::= { f3L3TrafficIPInterfaceEntry 39 }

f3L3TrafficIPIfDefaultGateway OBJECT-TYPE
    SYNTAX      Ipv6Address
    MAX-ACCESS  read-write
    STATUS      current
    DESCRIPTION
           "indicates active default GW of the interface."
    ::= { f3L3TrafficIPInterfaceEntry 40 }

f3L3TrafficIPIfIcmpErrorMsgRateLimit OBJECT-TYPE
    SYNTAX      Integer32
    MAX-ACCESS  read-write
    STATUS      current
    DESCRIPTION
           "limit originated ICMP error messages rate in number of messages per second.
            The value 0xFFFF shall be used to indicate no error message limit."
    ::= { f3L3TrafficIPInterfaceEntry 41 }

f3L3TrafficIPIfDhcpv6Role OBJECT-TYPE
    SYNTAX      CmDhcpRole
    MAX-ACCESS  read-write
    STATUS      current
    DESCRIPTION
           "Allows setting the DHCPv6 role on this interface."
    ::= { f3L3TrafficIPInterfaceEntry 42 }

f3L3TrafficIPIfDhcpv6Enabled OBJECT-TYPE
    SYNTAX      TruthValue
    MAX-ACCESS  read-write
    STATUS      current
    DESCRIPTION
           "Allows enabling/disabling of DHCPv6 on this interface."
    ::= { f3L3TrafficIPInterfaceEntry 43 }

f3L3TrafficIPIfDhcpRapidCommitControlEnabled OBJECT-TYPE
    SYNTAX      TruthValue
    MAX-ACCESS  read-write
    STATUS      current
    DESCRIPTION
           "This is the control to enable or disable DHCP rapid commit."
    ::= { f3L3TrafficIPInterfaceEntry 44 }

f3L3TrafficIPIfMaxRAInterval OBJECT-TYPE
    SYNTAX      Unsigned32
    MAX-ACCESS  read-write
    STATUS      current
    DESCRIPTION
           "Maximum time in seconds between generated RA messages."
    ::= { f3L3TrafficIPInterfaceEntry 45 }

f3L3TrafficIPIfMinRAInterval OBJECT-TYPE
    SYNTAX      Unsigned32
    MAX-ACCESS  read-write
    STATUS      current
    DESCRIPTION
           "Minimum time in seconds between generated RA messages,
            should be less than 0.75* max-ra-interval."
    ::= { f3L3TrafficIPInterfaceEntry 46 }

f3L3TrafficIPIfRouterLifeTime OBJECT-TYPE
    SYNTAX      Unsigned32
    MAX-ACCESS  read-write
    STATUS      current
    DESCRIPTION
           "Time in seconds the router can be used as a default router,
            should be larger than max-ra-interval."
    ::= { f3L3TrafficIPInterfaceEntry 47 }

f3L3TrafficIPIfReachableTime OBJECT-TYPE
    SYNTAX      Unsigned32
    MAX-ACCESS  read-write
    STATUS      current
    DESCRIPTION
           "time in milliseconds, that a node assumes a neighbor is reachable after having received
            a reachability confirmation, 0 means unspecified."
    ::= { f3L3TrafficIPInterfaceEntry 48 }

f3L3TrafficIPIfRaDhcpMoreConfigEnabled OBJECT-TYPE
    SYNTAX      TruthValue
    MAX-ACCESS  read-write
    STATUS      current
    DESCRIPTION
           "RA More configurations via DHCP."
    ::= { f3L3TrafficIPInterfaceEntry 49 }

f3L3TrafficIPIfRaManagedAddressConfigEnabled OBJECT-TYPE
    SYNTAX      TruthValue
    MAX-ACCESS  read-write
    STATUS      current
    DESCRIPTION
           "RA Managed Address Config Control."
    ::= { f3L3TrafficIPInterfaceEntry 50 }

f3L3TrafficIPIfRaRDNSSOptionEnabled OBJECT-TYPE
    SYNTAX      TruthValue
    MAX-ACCESS  read-write
    STATUS      current
    DESCRIPTION
           "Control Recursive DNS server option presence in the RA messages."
    ::= { f3L3TrafficIPInterfaceEntry 51 }

f3L3TrafficIPIfRaRDNSSLifeTime OBJECT-TYPE
    SYNTAX      Unsigned32
    MAX-ACCESS  read-write
    STATUS      current
    DESCRIPTION
           "Set the Lifetime field of the RDNSS option."
    ::= { f3L3TrafficIPInterfaceEntry 52 }

f3L3TrafficIPIfRaDNSSList OBJECT-TYPE
    SYNTAX      DisplayString
    MAX-ACCESS  read-write
    STATUS      current
    DESCRIPTION
           "list of IPv6 addresses of DNS servers."
    ::= { f3L3TrafficIPInterfaceEntry 53 }

f3L3TrafficIPIfRaDefaultRouterPreference OBJECT-TYPE
    SYNTAX      NdpRaDefaultRouterPreference
    MAX-ACCESS  read-write
    STATUS      current
    DESCRIPTION
           "Specifies Default Router preference field in RA according to RFC4191."
    ::= { f3L3TrafficIPInterfaceEntry 54 }

f3L3TrafficIPIfDupAddrDetectControl OBJECT-TYPE
    SYNTAX      TruthValue
    MAX-ACCESS  read-write
    STATUS      current
    DESCRIPTION
           "Allows enabling/disabling of DAD on this interface."
    ::= { f3L3TrafficIPInterfaceEntry 55 }

f3L3TrafficIPIfDupAddrDetectTransmits OBJECT-TYPE
    SYNTAX      Unsigned32
    MAX-ACCESS  read-write
    STATUS      current
    DESCRIPTION
           "Specify number of consequent NS messages sent by this interface."
    ::= { f3L3TrafficIPInterfaceEntry 56 }

f3L3TrafficIPIfDupAddrDetectRetransTimer OBJECT-TYPE
    SYNTAX      Unsigned32
    MAX-ACCESS  read-write
    STATUS      current
    DESCRIPTION
           "Interval in ms between consecutive NS messages and  as well as the time a node
            waits after sending the last NS  before ending the DAD."
    ::= { f3L3TrafficIPInterfaceEntry 57 }

f3L3TrafficIPIfMTU OBJECT-TYPE
    SYNTAX   Integer32
    MAX-ACCESS read-write
    STATUS   current
    DESCRIPTION
           "MTU of a L3 Traffic IP Interface in bytes."
    ::= { f3L3TrafficIPInterfaceEntry 58 }


--
-- Dhcp Relay Agent Traffic Ip Interface Member Table
--
f3DhcpRelayAgentTrafficIpIfMemberTable  OBJECT-TYPE
    SYNTAX      SEQUENCE OF F3DhcpRelayAgentTrafficIpIfMemberEntry
    MAX-ACCESS  not-accessible
    STATUS      current
    DESCRIPTION
            "A list of entries for the Dhcp Relay Agent Traffic Ip Interface member."
    ::= { f3L3Objects 10 }

f3DhcpRelayAgentTrafficIpIfMemberEntry  OBJECT-TYPE
    SYNTAX      F3DhcpRelayAgentTrafficIpIfMemberEntry
    MAX-ACCESS  not-accessible
    STATUS      current
    DESCRIPTION
            "A conceptual row in the f3DhcpRelayAgentTrafficIpIfMemberTable."
    INDEX { neIndex, f3DhcpRelayAgentIndex, f3DhcpRelayAgentTrafficIpIfMemberObject }
    ::= { f3DhcpRelayAgentTrafficIpIfMemberTable 1 }

F3DhcpRelayAgentTrafficIpIfMemberEntry ::= SEQUENCE {
    f3DhcpRelayAgentTrafficIpIfMemberObject             VariablePointer,
    f3DhcpRelayAgentTrafficIpIfMemberStorageType        StorageType,
    f3DhcpRelayAgentTrafficIpIfMemberRowStatus          RowStatus
}

f3DhcpRelayAgentTrafficIpIfMemberObject OBJECT-TYPE
    SYNTAX      VariablePointer
    MAX-ACCESS  not-accessible
    STATUS      current
    DESCRIPTION
           "This object describes the traffic ip interface."
    ::= { f3DhcpRelayAgentTrafficIpIfMemberEntry 1 }

f3DhcpRelayAgentTrafficIpIfMemberStorageType OBJECT-TYPE
    SYNTAX      StorageType
    MAX-ACCESS  read-create
    STATUS      current
    DESCRIPTION
           "The type of storage configured for this entry."
    ::= { f3DhcpRelayAgentTrafficIpIfMemberEntry 2 }

f3DhcpRelayAgentTrafficIpIfMemberRowStatus OBJECT-TYPE
    SYNTAX      RowStatus
    MAX-ACCESS  read-create
    STATUS      current
    DESCRIPTION
           "The status of this row.
          	An entry MUST NOT exist in the active state unless all
          	objects in the entry have an appropriate value, as described
          	in the description clause for each writable object.
 	
          	The values of f3DhcpRelayAgentTrafficIpIfMemberRowStatus supported are
          	createAndGo(4) and destroy(6).  All mandatory attributes
          	must be specified in a single SNMP SET request with
          	f3DhcpRelayAgentTrafficIpIfMemberRowStatus value as createAndGo(4).
          	Upon successful row creation, this object has a
          	value of active(1).
 	
          	The f3DhcpRelayAgentTrafficIpIfMemberRowStatus object may be modified if
          	the associated instance of this object is equal to active(1)."
    ::= { f3DhcpRelayAgentTrafficIpIfMemberEntry 3 }

---
---
---
f3VrfTrafficIpIfMemberTable  OBJECT-TYPE
    SYNTAX      SEQUENCE OF F3VrfTrafficIpIfMemberEntry
    MAX-ACCESS  not-accessible
    STATUS      current
    DESCRIPTION
            "A list of entries for the Vrf Traffic Ip Interface member."
    ::= { f3L3Objects 11 }

f3VrfTrafficIpIfMemberEntry  OBJECT-TYPE
    SYNTAX      F3VrfTrafficIpIfMemberEntry
    MAX-ACCESS  not-accessible
    STATUS      current
    DESCRIPTION
            "A conceptual row in the f3DhcpRelayAgentTrafficIpIfMemberTable."
    INDEX { neIndex, f3VrfIndex, f3VrfTrafficIpIfMemberObject }
    ::= { f3VrfTrafficIpIfMemberTable 1 }

F3VrfTrafficIpIfMemberEntry ::= SEQUENCE {
    f3VrfTrafficIpIfMemberObject             VariablePointer,
    f3VrfTrafficIpIfMemberStorageType        StorageType,
    f3VrfTrafficIpIfMemberRowStatus          RowStatus
}

f3VrfTrafficIpIfMemberObject OBJECT-TYPE
    SYNTAX      VariablePointer
    MAX-ACCESS  not-accessible
    STATUS      current
    DESCRIPTION
           "This object describes the traffic ip interface."
    ::= { f3VrfTrafficIpIfMemberEntry 1 }

f3VrfTrafficIpIfMemberStorageType OBJECT-TYPE
    SYNTAX      StorageType
    MAX-ACCESS  read-create
    STATUS      current
    DESCRIPTION
           "The type of storage configured for this entry."
    ::= { f3VrfTrafficIpIfMemberEntry 2 }

f3VrfTrafficIpIfMemberRowStatus OBJECT-TYPE
    SYNTAX      RowStatus
    MAX-ACCESS  read-create
    STATUS      current
    DESCRIPTION
           "The status of this row.
          	An entry MUST NOT exist in the active state unless all
          	objects in the entry have an appropriate value, as described
          	in the description clause for each writable object.
 	
          	The values of f3VrfTrafficIpIfMemberRowStatus supported are
          	createAndGo(4) and destroy(6).  All mandatory attributes
          	must be specified in a single SNMP SET request with
          	f3VrfTrafficIpIfMemberRowStatus value as createAndGo(4).
          	Upon successful row creation, this object has a
          	value of active(1).
 	
          	The f3VrfTrafficIpIfMemberRowStatus object may be modified if
          	the associated instance of this object is equal to active(1)."
    ::= { f3VrfTrafficIpIfMemberEntry 3 }

--
--  L3 taffic ipv4 route Table
--
f3L3TrafficIpv4RouteTable  OBJECT-TYPE
    SYNTAX      SEQUENCE OF F3L3TrafficIpv4RouteEntry
    MAX-ACCESS  not-accessible
    STATUS      deprecated
    DESCRIPTION
            "A list of entries for the L3 Traffic Ipv4 route.
             Must set f3VrfAction as retrieveEffectiveRoutes(4) before get data from this table."
    ::= { f3L3Objects 12 }

f3L3TrafficIpv4RouteEntry  OBJECT-TYPE
    SYNTAX      F3L3TrafficIpv4RouteEntry
    MAX-ACCESS  not-accessible
    STATUS      deprecated
    DESCRIPTION
            "A conceptual row in the f3L3TrafficIpv4RouteTable."
    INDEX { neIndex, f3VrfIndex, f3L3TrafficIpv4RouteDest, f3L3TrafficIpv4RouteMask, f3L3TrafficIpv4RouteNextHop, f3L3TrafficIpv4RouteInterface }
    ::= { f3L3TrafficIpv4RouteTable 1 }

F3L3TrafficIpv4RouteEntry ::= SEQUENCE {
    f3L3TrafficIpv4RouteDest                                IpAddress,
    f3L3TrafficIpv4RouteMask                                IpAddress,
    f3L3TrafficIpv4RouteNextHop                             IpAddress,
    f3L3TrafficIpv4RouteMetric                              Integer32,
    f3L3TrafficIpv4RouteInterface                           DisplayString,
    f3L3TrafficIpv4RouteAdvertise                           TruthValue,
    f3L3TrafficIpv4RouteStatus                              TrafficIpRouteStatus,
    f3L3TrafficIpv4RouteSourceForwardingEnable              TruthValue,
    f3L3TrafficIpv4RouteFlags                               RouteFlags,
    f3L3TrafficIpv4RouteStorageType                         StorageType,
    f3L3TrafficIpv4RouteRowStatus                           RowStatus,
    f3L3TrafficIpv4RouteType                                IpEntryType,
    f3L3TrafficIpv4RouteStatusX                             TrafficIpRouteStatusType,
    f3L3TrafficIpv4RouteOrigin                              TrafficIpRouteOriginType
}

f3L3TrafficIpv4RouteDest OBJECT-TYPE
    SYNTAX      IpAddress
    MAX-ACCESS  read-write
    STATUS      deprecated
    DESCRIPTION
           "It specifies the traffic Ipv4 route destination."
    ::= { f3L3TrafficIpv4RouteEntry 1 }

f3L3TrafficIpv4RouteMask OBJECT-TYPE
    SYNTAX      IpAddress
    MAX-ACCESS  read-write
    STATUS      deprecated
    DESCRIPTION
           "It specifies the traffic Ipv4 route mask."
    ::= { f3L3TrafficIpv4RouteEntry 2 }

f3L3TrafficIpv4RouteNextHop OBJECT-TYPE
    SYNTAX      IpAddress
    MAX-ACCESS  read-write
    STATUS      deprecated
    DESCRIPTION
           "It specifies the traffic Ipv4 route next hop."
    ::= { f3L3TrafficIpv4RouteEntry 3 }

f3L3TrafficIpv4RouteMetric OBJECT-TYPE
    SYNTAX      Integer32
    MAX-ACCESS  read-write
    STATUS      deprecated
    DESCRIPTION
           "It specifies the traffic Ipv4 route metric."
    ::= { f3L3TrafficIpv4RouteEntry 4 }

f3L3TrafficIpv4RouteInterface OBJECT-TYPE
    SYNTAX      DisplayString
    MAX-ACCESS  read-write
    STATUS      deprecated
    DESCRIPTION
           "It specifies the traffic Ipv4 route interface."
    ::= { f3L3TrafficIpv4RouteEntry 5 }

f3L3TrafficIpv4RouteAdvertise OBJECT-TYPE
    SYNTAX      TruthValue
    MAX-ACCESS  read-write
    STATUS      deprecated
    DESCRIPTION
           "It specifies the traffic Ipv4 route advertise."
    ::= { f3L3TrafficIpv4RouteEntry 6 }

f3L3TrafficIpv4RouteStatus OBJECT-TYPE
    SYNTAX      TrafficIpRouteStatus
    MAX-ACCESS  read-only
    STATUS      deprecated
    DESCRIPTION
           "It specifies the traffic Ipv4 route status.
            DEPRECATED and new attribute to use is
            f3L3TrafficIpv4RouteStatusX."
    ::= { f3L3TrafficIpv4RouteEntry 7 }

f3L3TrafficIpv4RouteSourceForwardingEnable OBJECT-TYPE
    SYNTAX      TruthValue
    MAX-ACCESS  read-write
    STATUS      deprecated
    DESCRIPTION
           "It specifies the traffic Ipv4 route source forwarding whether enabled."
    ::= { f3L3TrafficIpv4RouteEntry 8 }

f3L3TrafficIpv4RouteFlags OBJECT-TYPE
    SYNTAX      RouteFlags
    MAX-ACCESS  read-only
    STATUS      obsolete
    DESCRIPTION
           "It specifies the traffic Ipv4 route flags."
    ::= { f3L3TrafficIpv4RouteEntry 9 }

f3L3TrafficIpv4RouteStorageType OBJECT-TYPE
    SYNTAX      StorageType
    MAX-ACCESS  read-create
    STATUS      deprecated
    DESCRIPTION
           "The type of storage configured for this entry."
    ::= { f3L3TrafficIpv4RouteEntry 10 }

f3L3TrafficIpv4RouteRowStatus OBJECT-TYPE
    SYNTAX      RowStatus
    MAX-ACCESS  read-create
    STATUS      deprecated
    DESCRIPTION
           "The status of this row.
          	An entry MUST NOT exist in the active state unless all
          	objects in the entry have an appropriate value, as described
          	in the description clause for each writable object.
 	
          	The values of f3L3TrafficIpv4RouteRowStatus supported are
          	createAndGo(4) and destroy(6).  All mandatory attributes
          	must be specified in a single SNMP SET request with
          	f3L3TrafficIpv4RouteRowStatus value as createAndGo(4).
          	Upon successful row creation, this object has a
          	value of active(1).
 	
          	The f3L3TrafficIpv4RouteRowStatus object may be modified if
          	the associated instance of this object is equal to active(1)."
    ::= { f3L3TrafficIpv4RouteEntry 11 }

f3L3TrafficIpv4RouteType OBJECT-TYPE
    SYNTAX      IpEntryType
    MAX-ACCESS  read-only
    STATUS      deprecated
    DESCRIPTION
           "It specifies the route is dynamic or static."
    ::= { f3L3TrafficIpv4RouteEntry 12 }

f3L3TrafficIpv4RouteStatusX OBJECT-TYPE
    SYNTAX      TrafficIpRouteStatusType
    MAX-ACCESS  read-only
    STATUS      deprecated
    DESCRIPTION
           "It specifies the traffic Ipv4 route status."
    ::= { f3L3TrafficIpv4RouteEntry 13 }

f3L3TrafficIpv4RouteOrigin OBJECT-TYPE
    SYNTAX      TrafficIpRouteOriginType
    MAX-ACCESS  read-only
    STATUS      deprecated
    DESCRIPTION
        "The origin of IP Route."
   ::= { f3L3TrafficIpv4RouteEntry 14 }


--
--  L3 Traffic Arp Table 
--
f3L3TrafficArpTable  OBJECT-TYPE
    SYNTAX      SEQUENCE OF F3L3TrafficArpEntry
    MAX-ACCESS  not-accessible
    STATUS      current
    DESCRIPTION
            "A list of Traffic ARP entries on the NIDs.
             Must set f3L3TrafficIPIfActionX as optimizeArpRetrieve (1) before getting data from this table."
    ::= { f3L3Objects 13 }

f3L3TrafficArpEntry OBJECT-TYPE
    SYNTAX      F3L3TrafficArpEntry 
    MAX-ACCESS  not-accessible
    STATUS      current
    DESCRIPTION
            "A conceptual row in the f3L3TrafficArpTable. Entries can
             be created/deleted in this table by management application action."
    INDEX { neIndex, shelfIndex, slotIndex,
            f3L3FlowPointPortIndex, f3L3FlowPointIndex, f3L3TrafficIPIfIndex, f3L3TrafficArpIPAddress }
    ::= { f3L3TrafficArpTable 1 }

F3L3TrafficArpEntry ::= SEQUENCE {
    f3L3TrafficArpIPAddress      IpAddress,
    f3L3TrafficArpMacAddress     MacAddress,
    f3L3TrafficArpInterface      DisplayString,
    f3L3TrafficArpEntryType      IpEntryType,
    f3L3TrafficArpStorageType    StorageType,
    f3L3TrafficArpRowStatus      RowStatus
}

f3L3TrafficArpIPAddress OBJECT-TYPE
    SYNTAX     IpAddress
    MAX-ACCESS not-accessible
    STATUS     current
    DESCRIPTION
         "This object allows configuration of the ARP Entry IP Address."
     ::= { f3L3TrafficArpEntry 1 }

f3L3TrafficArpMacAddress OBJECT-TYPE
    SYNTAX     MacAddress
    MAX-ACCESS read-create
    STATUS     current
    DESCRIPTION
         "This object allows management of the ARP Entry MAC Address."
     ::= { f3L3TrafficArpEntry 2 }

f3L3TrafficArpInterface OBJECT-TYPE
    SYNTAX     DisplayString
    MAX-ACCESS read-only
    STATUS     current
    DESCRIPTION
         "This object allows management of the ARP Entry Interface."
     ::= { f3L3TrafficArpEntry 3 }

f3L3TrafficArpEntryType OBJECT-TYPE
    SYNTAX     IpEntryType
    MAX-ACCESS read-write 
    STATUS     current
    DESCRIPTION
            "The type of ARP Entry. Note that static entries can be created."
    ::= { f3L3TrafficArpEntry 4 }

f3L3TrafficArpStorageType OBJECT-TYPE
    SYNTAX     StorageType
    MAX-ACCESS read-create
    STATUS     current
    DESCRIPTION
            "The type of storage configured for this entry."
    ::= { f3L3TrafficArpEntry 5 }

f3L3TrafficArpRowStatus OBJECT-TYPE
    SYNTAX      RowStatus
    MAX-ACCESS  read-write
    STATUS      current
    DESCRIPTION
            "The status of this row.
             The f3L3TrafficArpRowStatus object may be modified if
             the associated instance of this object is equal to active(1),
             notInService(2), or notReady(3)."
    ::= { f3L3TrafficArpEntry 6 }


--
--  L3 Traffic BGP Router Table 
--
f3L3TrafficBgpRouterTable  OBJECT-TYPE
    SYNTAX      SEQUENCE OF F3L3TrafficBgpRouterEntry
    MAX-ACCESS  not-accessible
    STATUS      current
    DESCRIPTION
            "Traffic BGP Router."
    ::= { f3L3Objects 14 }

f3L3TrafficBgpRouterEntry OBJECT-TYPE
    SYNTAX      F3L3TrafficBgpRouterEntry 
    MAX-ACCESS  not-accessible
    STATUS      current
    DESCRIPTION
            "A conceptual row in the f3L3TrafficBgpRouterTable. Entries can
            be created/deleted in this table by management application action."
    INDEX { neIndex, f3VrfIndex, f3L3TrafficBgpRouterIndex }
    ::= { f3L3TrafficBgpRouterTable 1 }

F3L3TrafficBgpRouterEntry ::= SEQUENCE {
    f3L3TrafficBgpRouterIndex                          Unsigned32,
    f3L3TrafficBgpRouterAdminState                     AdminState,
    f3L3TrafficBgpRouterSecondaryState                 SecondaryState,
    f3L3TrafficBgpRouterOperationalState               OperationalState,
    f3L3TrafficBgpRouterId                             IpAddress,
    f3L3TrafficBgpRouterAsNumber                       Unsigned32,
    f3L3TrafficBgpRouterConnectedRoutesRedistControl   TruthValue,
    f3L3TrafficBgpRouterOspfRoutesRedistControl        TruthValue,
    f3L3TrafficBgpRouterStaticRoutesRedistControl      TruthValue,
    f3L3TrafficBgpRouterDhcpRoutesRedistControl        TruthValue,
    f3L3TrafficBgpRouterStorageType                    StorageType,
    f3L3TrafficBgpRouterRowStatus                      RowStatus,
    f3L3TrafficBgpRouterAction                         BgpRouterActionType,
    f3L3TrafficBgpRouterIBgpAdminDistance              Unsigned32,
    f3L3TrafficBgpRouterEBgpAdminDistance              Unsigned32,
    f3L3TrafficBgpRouterEcmpMaximumPaths               Unsigned32,
    f3L3TrafficBgpRouterRestartTime                    Unsigned32,
    f3L3TrafficBgpRouterStaleRoutesTime                Unsigned32
}

f3L3TrafficBgpRouterIndex OBJECT-TYPE
    SYNTAX      Unsigned32
    MAX-ACCESS  not-accessible
    STATUS      current
    DESCRIPTION
        "The ID of BGP router."
   ::= { f3L3TrafficBgpRouterEntry 1 }

f3L3TrafficBgpRouterAdminState OBJECT-TYPE
    SYNTAX      AdminState 
    MAX-ACCESS  read-write
    STATUS      current
    DESCRIPTION
            "This object represents the Administrative State of the Traffic BGP Router."
    ::= { f3L3TrafficBgpRouterEntry 2 }

f3L3TrafficBgpRouterSecondaryState OBJECT-TYPE
    SYNTAX      SecondaryState 
    MAX-ACCESS  read-only
    STATUS      current
    DESCRIPTION
            "This object represents the Secondary State of the Traffic BGP Router."
    ::= { f3L3TrafficBgpRouterEntry 3 }

f3L3TrafficBgpRouterOperationalState OBJECT-TYPE
    SYNTAX      OperationalState 
    MAX-ACCESS  read-only
    STATUS      current
    DESCRIPTION
            "This object represents the Operational State of the Traffic BGP Router."
    ::= { f3L3TrafficBgpRouterEntry 4 }

f3L3TrafficBgpRouterId OBJECT-TYPE
    SYNTAX      IpAddress
    MAX-ACCESS  read-write
    STATUS      current
    DESCRIPTION
           "BGP Router Identifier."
    ::= { f3L3TrafficBgpRouterEntry 5 }

f3L3TrafficBgpRouterAsNumber OBJECT-TYPE
    SYNTAX      Unsigned32
    MAX-ACCESS  read-write
    STATUS      current
    DESCRIPTION
           "Local autonomous system number of the router.  Uses
            the 32-bit as-number type from the model in RFC 6991."
    ::= { f3L3TrafficBgpRouterEntry 6 }

f3L3TrafficBgpRouterConnectedRoutesRedistControl OBJECT-TYPE
    SYNTAX      TruthValue
    MAX-ACCESS  read-write
    STATUS      deprecated
    DESCRIPTION
           "This attribute is used to control connected route redistribution into BGP."
    ::= { f3L3TrafficBgpRouterEntry 7 }

f3L3TrafficBgpRouterOspfRoutesRedistControl OBJECT-TYPE
    SYNTAX      TruthValue
    MAX-ACCESS  read-write
    STATUS      deprecated
    DESCRIPTION
           "This attribute specifies OSPF route redistribution options 
            False - OSPF routes are not redistributed to the BGP 
            True - OSPF routes are redistributed to BGP."
    ::= { f3L3TrafficBgpRouterEntry 8 }

f3L3TrafficBgpRouterStaticRoutesRedistControl OBJECT-TYPE
    SYNTAX      TruthValue
    MAX-ACCESS  read-write
    STATUS      deprecated
    DESCRIPTION
           "This attribute is used to control static route redistribution into BGP."
    ::= { f3L3TrafficBgpRouterEntry 9 }

f3L3TrafficBgpRouterDhcpRoutesRedistControl OBJECT-TYPE
    SYNTAX      TruthValue
    MAX-ACCESS  read-write
    STATUS      deprecated
    DESCRIPTION
           "This attribute is used to control DHCP route redistribution into BGP."
    ::= { f3L3TrafficBgpRouterEntry 10 }

f3L3TrafficBgpRouterStorageType OBJECT-TYPE
    SYNTAX      StorageType
    MAX-ACCESS  read-create
    STATUS      current
    DESCRIPTION
        "The storage type for this conceptual row."
   ::= { f3L3TrafficBgpRouterEntry 11 }

f3L3TrafficBgpRouterRowStatus OBJECT-TYPE
    SYNTAX      RowStatus
    MAX-ACCESS  read-create
    STATUS      current
    DESCRIPTION
        "The status of this row.  An entry MUST NOT exist in the 
        active state unless all objects in the entry have an 
        appropriate value, as described
        in the description clause for each writable object.

        The values of f3L3TrafficBgpRouterRowStatus supported are
        createAndGo(4) and destroy(6).  All mandatory attributes
        must be specified in a single SNMP SET request with
        f3L3TrafficBgpRouterRowStatus value as createAndGo(4).
        Upon successful row creation, this object has a
        value of active(1).

        The f3L3TrafficBgpRouterRowStatus object may be modified if
        the associated instance of this object is equal to active(1)."
   ::= { f3L3TrafficBgpRouterEntry 12 }

f3L3TrafficBgpRouterAction OBJECT-TYPE
    SYNTAX      BgpRouterActionType
    MAX-ACCESS  read-write
    STATUS      current
    DESCRIPTION
           "This object describes action set on this BGP Router."
    ::= { f3L3TrafficBgpRouterEntry 13 }

f3L3TrafficBgpRouterIBgpAdminDistance OBJECT-TYPE
    SYNTAX      Unsigned32
    MAX-ACCESS  read-write
    STATUS      current
    DESCRIPTION
           "Administrative distance for routes learned from internal
            BGP (iBGP)."
    ::= { f3L3TrafficBgpRouterEntry 14 }

f3L3TrafficBgpRouterEBgpAdminDistance OBJECT-TYPE
    SYNTAX      Unsigned32
    MAX-ACCESS  read-write
    STATUS      current
    DESCRIPTION
           "Administrative distance for routes learned from external
            BGP (eBGP)."
    ::= { f3L3TrafficBgpRouterEntry 15 }

f3L3TrafficBgpRouterEcmpMaximumPaths OBJECT-TYPE
    SYNTAX      Unsigned32
    MAX-ACCESS  read-write
    STATUS      current
    DESCRIPTION
           "The maximum number of path used in ECMP for BGP routes."
    ::= { f3L3TrafficBgpRouterEntry 16 }

f3L3TrafficBgpRouterRestartTime OBJECT-TYPE
    SYNTAX      Unsigned32
    MAX-ACCESS  read-write
    STATUS      current
    DESCRIPTION
           "Estimated time (in seconds) for the local BGP speaker to 
            restart a session.This value is advertise in the graceful
            restart BGP capability. This is a 12-bit value, referred to
            as Restart Time in RFC4724. Per RFC4724, the suggested
            default value is <= the hold-time value."
    ::= { f3L3TrafficBgpRouterEntry 17 }

f3L3TrafficBgpRouterStaleRoutesTime OBJECT-TYPE
    SYNTAX      Unsigned32
    MAX-ACCESS  read-write
    STATUS      current
    DESCRIPTION
           "An upper-bound on the time that stale routes will be
            retained by a router after a session is restarted. 
            If an End-of-RIB (EOR) marker is received prior to this timer
            expiring stale-routes will be flushed upon its 
            receipt - if no EOR is received, then when this timer 
            expires stale paths will be purged. This timer is referred 
            to as the Selection_Deferral_Timer in FC4724."
    ::= { f3L3TrafficBgpRouterEntry 18 }


--
--  L3 Traffic BGP Route Table 
--

f3L3TrafficBgpRouteTable  OBJECT-TYPE
    SYNTAX      SEQUENCE OF F3L3TrafficBgpRouteEntry
    MAX-ACCESS  not-accessible
    STATUS      current
    DESCRIPTION
            "BGP routes.
             Must set f3L3TrafficBgpRouterAction as optimizeBgpRouteRetrieve(1) before get data from this table."
    ::= { f3L3Objects 15 }

f3L3TrafficBgpRouteEntry OBJECT-TYPE
    SYNTAX      F3L3TrafficBgpRouteEntry 
    MAX-ACCESS  not-accessible
    STATUS      current
    DESCRIPTION
            "A conceptual row in the f3L3TrafficBgpRouteTable. Entries can
            be created/deleted in this table by management application action."
    INDEX { neIndex, 
            f3VrfIndex, 
            f3L3TrafficBgpRouterIndex,
            f3L3TrafficBgpRouteNetwork,
            f3L3TrafficBgpRouteMetric,
            f3L3TrafficBgpRouteNextHop }
    ::= { f3L3TrafficBgpRouteTable 1 }

F3L3TrafficBgpRouteEntry ::= SEQUENCE {
    f3L3TrafficBgpRouteNetwork                   IpAddress,
    f3L3TrafficBgpRouteMetric                    Unsigned32,
    f3L3TrafficBgpRouteNextHop                   IpAddress,
    f3L3TrafficBgpRoutePath                      DisplayString
}

f3L3TrafficBgpRouteNetwork OBJECT-TYPE
    SYNTAX      IpAddress
    MAX-ACCESS  not-accessible
    STATUS      current
    DESCRIPTION
        "Network of destination. Key of the table."
   ::= { f3L3TrafficBgpRouteEntry 1 }

f3L3TrafficBgpRouteMetric OBJECT-TYPE
    SYNTAX      Unsigned32
    MAX-ACCESS  not-accessible
    STATUS      current
    DESCRIPTION
        "Metric value of this route. Key of the table."
   ::= { f3L3TrafficBgpRouteEntry 2 }

f3L3TrafficBgpRouteNextHop OBJECT-TYPE
    SYNTAX      IpAddress
    MAX-ACCESS  not-accessible
    STATUS      current
    DESCRIPTION
        "IP address of next hop. Key of the table."
   ::= { f3L3TrafficBgpRouteEntry 3 }

f3L3TrafficBgpRoutePath OBJECT-TYPE
    SYNTAX      DisplayString (SIZE(0..1024))
    MAX-ACCESS  read-only
    STATUS      current
    DESCRIPTION
        "The list of AS numbers to the destination."
   ::= { f3L3TrafficBgpRouteEntry 4 }


--
--  L3 Traffic BGP Peer Table 
--

f3L3TrafficBgpPeerTable  OBJECT-TYPE
    SYNTAX      SEQUENCE OF F3L3TrafficBgpPeerEntry
    MAX-ACCESS  not-accessible
    STATUS      current
    DESCRIPTION
            "Traffic BGP peer."
    ::= { f3L3Objects 16 }

f3L3TrafficBgpPeerEntry OBJECT-TYPE
    SYNTAX      F3L3TrafficBgpPeerEntry 
    MAX-ACCESS  not-accessible
    STATUS      current
    DESCRIPTION
            "A conceptual row in the f3L3TrafficBgpPeerTable. Entries can
            be created/deleted in this table by management application action."
    INDEX { neIndex, f3VrfIndex, f3L3TrafficBgpRouterIndex, f3L3TrafficBgpPeerIndex }
    ::= { f3L3TrafficBgpPeerTable 1 }

F3L3TrafficBgpPeerEntry ::= SEQUENCE {
    f3L3TrafficBgpPeerIndex                          Unsigned32,
    f3L3TrafficBgpPeerAdminState                     AdminState,
    f3L3TrafficBgpPeerSecondaryState                 SecondaryState,
    f3L3TrafficBgpPeerOperationalState               OperationalState,
    f3L3TrafficBgpPeerIpv4Addr                       IpAddress,
    f3L3TrafficBgpPeerAsNumber                       Unsigned32,
    f3L3TrafficBgpPeerDescription                    DisplayString,
    f3L3TrafficBgpPeerBgpSessionState                BgpSessionStateType,
    f3L3TrafficBgpPeerHoldTime                       Unsigned32,
    f3L3TrafficBgpPeerStartupHoldTime                Unsigned32,
    f3L3TrafficBgpPeerKeepAliveTime                  Unsigned32,
    f3L3TrafficBgpPeerConnectRetryTime               Unsigned32,
    f3L3TrafficBgpPeerUpdateSourceIp                 IpAddress,
    f3L3TrafficBgpPeerAuthenticationKey              VariablePointer,
    f3L3TrafficBgpPeerTimeSinceUpTransition          Unsigned32,
    f3L3TrafficBgpPeerTimeSinceDownTransition        Unsigned32,
    f3L3TrafficBgpPeerStorageType                    StorageType,
    f3L3TrafficBgpPeerRowStatus                      RowStatus,
    f3L3TrafficBgpPeerIpVersion                      IpVersion,
    f3L3TrafficBgpPeerIpv6Address                    Ipv6Address,
    f3L3TrafficBgpPeerUpdateSourceIpv6               Ipv6Address,
    f3L3TrafficBgpPeerMultihopControl                TruthValue,
    f3L3TrafficBgpPeerMultihopTtl                    Unsigned32,
    f3L3TrafficBgpPeerUpdateSourceInterface          DisplayString,
    f3L3TrafficBgpPeerUpdateSourceType               BgpUpdateSourceType,
    f3L3TrafficBgpPeerLocalPreference                Unsigned32,
    f3L3TrafficBgpPeerRouteReflectorClient           TruthValue,
    f3L3TrafficBgpPeerRouteReflectorClusterId        IpAddress,
    f3L3TrafficBgpPeerBgpRouteInboundFilter          DisplayString,
    f3L3TrafficBgpPeerBgpRouteOutboundFilter         DisplayString,
    f3L3TrafficBgpPeerBgpGracefulRestart             BgpGracefulRestartControlType,
    f3L3TrafficBgpPeerPeerRestartTime                Unsigned32,
    f3L3TrafficBgpPeerPeerRestarting                 TruthValue
}

f3L3TrafficBgpPeerIndex OBJECT-TYPE
    SYNTAX      Unsigned32
    MAX-ACCESS  not-accessible
    STATUS      current
    DESCRIPTION
        "The ID of BGP peer instance."
   ::= { f3L3TrafficBgpPeerEntry 1 }

f3L3TrafficBgpPeerAdminState OBJECT-TYPE
    SYNTAX      AdminState 
    MAX-ACCESS  read-write
    STATUS      current
    DESCRIPTION
            "This object represents the Administrative State of the Traffic BGP Peer."
    ::= { f3L3TrafficBgpPeerEntry 2 }

f3L3TrafficBgpPeerSecondaryState OBJECT-TYPE
    SYNTAX      SecondaryState 
    MAX-ACCESS  read-only
    STATUS      current
    DESCRIPTION
            "This object represents the Secondary State of the Traffic BGP Peer."
    ::= { f3L3TrafficBgpPeerEntry 3 }

f3L3TrafficBgpPeerOperationalState OBJECT-TYPE
    SYNTAX      OperationalState 
    MAX-ACCESS  read-only
    STATUS      current
    DESCRIPTION
            "This object represents the Operational State of the Traffic BGP Peer."
    ::= { f3L3TrafficBgpPeerEntry 4 }

f3L3TrafficBgpPeerIpv4Addr OBJECT-TYPE
    SYNTAX      IpAddress
    MAX-ACCESS  read-write
    STATUS      current
    DESCRIPTION
           "BGP Neighbor IP address."
    ::= { f3L3TrafficBgpPeerEntry 5 }

f3L3TrafficBgpPeerAsNumber OBJECT-TYPE
    SYNTAX      Unsigned32
    MAX-ACCESS  read-write
    STATUS      current
    DESCRIPTION
           "AS number of the peer."
    ::= { f3L3TrafficBgpPeerEntry 6 }

f3L3TrafficBgpPeerDescription OBJECT-TYPE
    SYNTAX      DisplayString (SIZE(0..256))
    MAX-ACCESS  read-write
    STATUS      current
    DESCRIPTION
           "An optional textual description intended primarily for use
            with a peer or group."
    ::= { f3L3TrafficBgpPeerEntry 7 }

f3L3TrafficBgpPeerBgpSessionState OBJECT-TYPE
    SYNTAX      BgpSessionStateType
    MAX-ACCESS  read-only
    STATUS      current
    DESCRIPTION
           "This attribute indicates BGP session state."
    ::= { f3L3TrafficBgpPeerEntry 8 }

f3L3TrafficBgpPeerHoldTime OBJECT-TYPE
    SYNTAX      Unsigned32
    MAX-ACCESS  read-write
    STATUS      current
    DESCRIPTION
           "Time interval in seconds that a BGP session will be
            considered active in the absence of keepalive or other
            messages from the peer.  The hold-time is typically
            set to 3x the keepalive-interval."
    ::= { f3L3TrafficBgpPeerEntry 9 }

f3L3TrafficBgpPeerStartupHoldTime OBJECT-TYPE
    SYNTAX      Unsigned32
    MAX-ACCESS  read-write
    STATUS      current
    DESCRIPTION
           "Value of the hold timer used before the routers have a 
            chance to exchange open messages and agree on the real value."
    ::= { f3L3TrafficBgpPeerEntry 10 }

f3L3TrafficBgpPeerKeepAliveTime OBJECT-TYPE
    SYNTAX      Unsigned32
    MAX-ACCESS  read-write
    STATUS      current
    DESCRIPTION
           "Time interval in seconds between transmission of keepalive
            messages to the neighbor.  Typically set to 1/3 the
            hold-time."
    ::= { f3L3TrafficBgpPeerEntry 11 }

f3L3TrafficBgpPeerConnectRetryTime OBJECT-TYPE
    SYNTAX      Unsigned32
    MAX-ACCESS  read-write
    STATUS      current
    DESCRIPTION
           "Time interval in seconds between attempts to establish a
            session with the peer."
    ::= { f3L3TrafficBgpPeerEntry 12 }

f3L3TrafficBgpPeerUpdateSourceIp OBJECT-TYPE
    SYNTAX      IpAddress
    MAX-ACCESS  read-write
    STATUS      current
    DESCRIPTION
           "IP address used to update the source IP of BGP message transmitted.
            Normally loopback interface IP may be used to support loadsharing/redundancy 
            between local and peer. Default value 0.0.0.0 implies no update."
    ::= { f3L3TrafficBgpPeerEntry 13 }

f3L3TrafficBgpPeerAuthenticationKey OBJECT-TYPE
    SYNTAX      VariablePointer
    MAX-ACCESS  read-write
    STATUS      current
    DESCRIPTION
           "Authentication Key used with neighboring devices."
    ::= { f3L3TrafficBgpPeerEntry 14 }

f3L3TrafficBgpPeerTimeSinceUpTransition OBJECT-TYPE
    SYNTAX      Unsigned32
    MAX-ACCESS  read-only
    STATUS      current
    DESCRIPTION
           "Number of seconds since last transition to Established state."
    ::= { f3L3TrafficBgpPeerEntry 15 }

f3L3TrafficBgpPeerTimeSinceDownTransition OBJECT-TYPE
    SYNTAX      Unsigned32
    MAX-ACCESS  read-only
    STATUS      current
    DESCRIPTION
           "Number of seconds since last transition out of Established state."
    ::= { f3L3TrafficBgpPeerEntry 16 }

f3L3TrafficBgpPeerStorageType OBJECT-TYPE
    SYNTAX      StorageType
    MAX-ACCESS  read-create
    STATUS      current
    DESCRIPTION
        "The storage type for this conceptual row."
   ::= { f3L3TrafficBgpPeerEntry 17 }

f3L3TrafficBgpPeerRowStatus OBJECT-TYPE
    SYNTAX      RowStatus
    MAX-ACCESS  read-create
    STATUS      current
    DESCRIPTION
        "The status of this row.  An entry MUST NOT exist in the 
        active state unless all objects in the entry have an 
        appropriate value, as described
        in the description clause for each writable object.

        The values of f3L3TrafficBgpPeerRowStatus supported are
        createAndGo(4) and destroy(6).  All mandatory attributes
        must be specified in a single SNMP SET request with
        f3L3TrafficBgpPeerRowStatus value as createAndGo(4).
        Upon successful row creation, this object has a
        value of active(1).

        The f3L3TrafficBgpPeerRowStatus object may be modified if
        the associated instance of this object is equal to active(1)."
   ::= { f3L3TrafficBgpPeerEntry 18 }

f3L3TrafficBgpPeerIpVersion OBJECT-TYPE
    SYNTAX      IpVersion
    MAX-ACCESS  read-write
    STATUS      current
    DESCRIPTION
           "This attribute is supported on ge11x units."
    ::= { f3L3TrafficBgpPeerEntry 19 }

f3L3TrafficBgpPeerIpv6Address OBJECT-TYPE
    SYNTAX      Ipv6Address
    MAX-ACCESS  read-write
    STATUS      current
    DESCRIPTION
           "This attribute is supported on ge11x units."
    ::= { f3L3TrafficBgpPeerEntry 20 }

f3L3TrafficBgpPeerUpdateSourceIpv6 OBJECT-TYPE
    SYNTAX      Ipv6Address
    MAX-ACCESS  read-write
    STATUS      current
    DESCRIPTION
           "This attribute is supported on ge11x units."
    ::= { f3L3TrafficBgpPeerEntry 21 }

f3L3TrafficBgpPeerMultihopControl OBJECT-TYPE
    SYNTAX      TruthValue
    MAX-ACCESS  read-write
    STATUS      current
    DESCRIPTION
           "This attribute is supported on ge11x units."
    ::= { f3L3TrafficBgpPeerEntry 22 }

f3L3TrafficBgpPeerMultihopTtl OBJECT-TYPE
    SYNTAX      Unsigned32
    MAX-ACCESS  read-write
    STATUS      current
    DESCRIPTION
           "This attribute is supported on ge11x units."
    ::= { f3L3TrafficBgpPeerEntry 23 }

f3L3TrafficBgpPeerUpdateSourceInterface OBJECT-TYPE
    SYNTAX      DisplayString
    MAX-ACCESS  read-write
    STATUS      current
    DESCRIPTION
           "This attribute is supported on ge11x units."
    ::= { f3L3TrafficBgpPeerEntry 24 }

f3L3TrafficBgpPeerUpdateSourceType OBJECT-TYPE
    SYNTAX      BgpUpdateSourceType
    MAX-ACCESS  read-write
    STATUS      current
    DESCRIPTION
           "This attribute is supported on ge11x units."
    ::= { f3L3TrafficBgpPeerEntry 25 }

f3L3TrafficBgpPeerLocalPreference OBJECT-TYPE
    SYNTAX      Unsigned32
    MAX-ACCESS  read-write
    STATUS      current
    DESCRIPTION
           "This attribute is supported on ge11x/xgpro units."
    ::= { f3L3TrafficBgpPeerEntry 26 }

f3L3TrafficBgpPeerRouteReflectorClient OBJECT-TYPE
    SYNTAX      TruthValue
    MAX-ACCESS  read-write
    STATUS      current
    DESCRIPTION
           "This attribute is supported on ge11x/xgpro units."
    ::= { f3L3TrafficBgpPeerEntry 27 }

f3L3TrafficBgpPeerRouteReflectorClusterId OBJECT-TYPE
    SYNTAX      IpAddress
    MAX-ACCESS  read-write
    STATUS      current
    DESCRIPTION
           "This attribute is supported on ge11x/xgpro units."
    ::= { f3L3TrafficBgpPeerEntry 28 }

f3L3TrafficBgpPeerBgpRouteInboundFilter OBJECT-TYPE
    SYNTAX      DisplayString
    MAX-ACCESS  read-write
    STATUS      current
    DESCRIPTION
           "This is the name of the IP Prefix List that is used as the filter for 
            Inbound. This is a read-write value. A null string implies there is no filter."
    ::= { f3L3TrafficBgpPeerEntry 29 }

f3L3TrafficBgpPeerBgpRouteOutboundFilter OBJECT-TYPE
    SYNTAX      DisplayString
    MAX-ACCESS  read-write
    STATUS      current
    DESCRIPTION
           "This is the name of the IP Prefix List that is used as the filter for Inbound. 
            This is a read-write value. A null string implies there is no filter."
    ::= { f3L3TrafficBgpPeerEntry 30 }

f3L3TrafficBgpPeerBgpGracefulRestart OBJECT-TYPE
    SYNTAX      BgpGracefulRestartControlType
    MAX-ACCESS  read-write
    STATUS      current
    DESCRIPTION
           "Enable or disable the graceful restart capability. 
            Helper_only means the router does not support local restarting, 
            but able to assist remote peer's restart.."
    ::= { f3L3TrafficBgpPeerEntry 31 }

f3L3TrafficBgpPeerPeerRestartTime OBJECT-TYPE
    SYNTAX      Unsigned32
    MAX-ACCESS  read-only
    STATUS      current
    DESCRIPTION
           "The period of time (advertised by the peer) that the peer 
            expects a restart of a BGP session to take.."
    ::= { f3L3TrafficBgpPeerEntry 32 }

f3L3TrafficBgpPeerPeerRestarting OBJECT-TYPE
    SYNTAX      TruthValue
    MAX-ACCESS  read-only
    STATUS      current
    DESCRIPTION
           "This flag indicates whether the remote neighbor is currently 
            in the process of restarting, and hence received routes are 
            currently stale."
    ::= { f3L3TrafficBgpPeerEntry 33 }


--
-- OSPF Router
--

f3VrfOspfRouterTable OBJECT-TYPE
    SYNTAX      SEQUENCE OF F3VrfOspfRouterEntry
    MAX-ACCESS  not-accessible
    STATUS      current
    DESCRIPTION
        "OSPF Router."

   ::= { f3L3Objects 17 }

f3VrfOspfRouterEntry OBJECT-TYPE
    SYNTAX      F3VrfOspfRouterEntry
    MAX-ACCESS  not-accessible
    STATUS      current
    DESCRIPTION
        "A conceptual row in f3VrfOspfRouterTable."
    INDEX   { neIndex, 
              f3VrfIndex,
              f3VrfOspfRouterIndex }

   ::= { f3VrfOspfRouterTable 1 }

F3VrfOspfRouterEntry ::= SEQUENCE {
    f3VrfOspfRouterIndex                             Unsigned32,
    f3VrfOspfRouterAdminState                        AdminState,
    f3VrfOspfRouterSecondaryState                    SecondaryState,
    f3VrfOspfRouterOperationalState                  OperationalState,
    f3VrfOspfRouterId                                IpAddress,
    f3VrfOspfRouterDescription                       DisplayString,
    f3VrfOspfRouterBgpRoutesRedistributeToOspf       TruthValue,
    f3VrfOspfRouterBgpRoutesMetricType               RoutesMetricType,
    f3VrfOspfRouterBgpRoutesMetric                   Unsigned32,
    f3VrfOspfRouterStaticRoutesRedistributeToOspf    TruthValue,
    f3VrfOspfRouterStaticRoutesMetricType            RoutesMetricType,
    f3VrfOspfRouterStaticRoutesMetric                Unsigned32,
    f3VrfOspfRouterConnectedRoutesRedistributeToOspf TruthValue,
    f3VrfOspfRouterConnectedRoutesMetricType         RoutesMetricType,
    f3VrfOspfRouterConnectedRoutesMetric             Unsigned32,
    f3VrfOspfRouterDhcpRoutesRedistributeToOspf      TruthValue,
    f3VrfOspfRouterDhcpRoutesMetricType              RoutesMetricType,
    f3VrfOspfRouterDhcpRoutesMetric                  Unsigned32,
    f3VrfOspfRouterIsAbr                             TruthValue,
    f3VrfOspfRouterIsAsbr                            TruthValue,
    f3VrfOspfRouterStorageType                       StorageType,
    f3VrfOspfRouterRowStatus                         RowStatus,
    f3VrfOspfRouterAction                            OspfRouterActionType,
    f3VrfOspfRouterVersion                           OspfVersion,
    f3VrfOspfRouterAdministrativeDistance            Unsigned32,
    f3VrfOspfRouterSlaacRoutesRedistributeToOspf     TruthValue,
    f3VrfOspfRouterSlaacRoutesMetricType             RoutesMetricType,
    f3VrfOspfRouterSlaacRoutesMetric                 Unsigned32,
    f3VrfOspfRouterEcmpMaximumPaths                  Unsigned32,
    f3VrfOspfRouterSrControl                         TruthValue,
    f3VrfOspfRouterConvergenceTime                   Unsigned32
}

f3VrfOspfRouterIndex OBJECT-TYPE
    SYNTAX      Unsigned32
    MAX-ACCESS  not-accessible
    STATUS      current
    DESCRIPTION
        "The ID of OSPF Router instance."
   ::= { f3VrfOspfRouterEntry 1 }

f3VrfOspfRouterAdminState OBJECT-TYPE
    SYNTAX      AdminState
    MAX-ACCESS  read-write
    STATUS      current
    DESCRIPTION
            "This object represents the Administrative State of the Traffic OSPF Router." 
    ::= { f3VrfOspfRouterEntry 2 }

f3VrfOspfRouterSecondaryState OBJECT-TYPE
    SYNTAX      SecondaryState
    MAX-ACCESS  read-only
    STATUS      current
    DESCRIPTION
            "This object represents the Secondary State of the Traffic OSPF Router." 
    ::= { f3VrfOspfRouterEntry 3 }

f3VrfOspfRouterOperationalState OBJECT-TYPE
    SYNTAX      OperationalState
    MAX-ACCESS  read-only
    STATUS      current
    DESCRIPTION
            "This object represents the Operational State of the Traffic OSPF Router." 
    ::= { f3VrfOspfRouterEntry 4 }

f3VrfOspfRouterId OBJECT-TYPE
    SYNTAX  IpAddress
    MAX-ACCESS  read-write
    STATUS  current
    DESCRIPTION
        "IP address used as Router ID for the OSPF protocol."
    ::= { f3VrfOspfRouterEntry 5 }

f3VrfOspfRouterDescription OBJECT-TYPE
    SYNTAX  DisplayString (SIZE(0..256))
    MAX-ACCESS  read-write
    STATUS  current
    DESCRIPTION
        "The description of OSPF router."
    ::= { f3VrfOspfRouterEntry 6 }

f3VrfOspfRouterBgpRoutesRedistributeToOspf OBJECT-TYPE
    SYNTAX  TruthValue
    MAX-ACCESS  read-write
    STATUS  current
    DESCRIPTION
        "This attribute is used to control redistribution of dynamic routes learnt 
         via BGP into OSPF."
    ::= { f3VrfOspfRouterEntry 7 }

f3VrfOspfRouterBgpRoutesMetricType OBJECT-TYPE
    SYNTAX  RoutesMetricType
    MAX-ACCESS  read-write
    STATUS  current
    DESCRIPTION
        "Metric type of the BGP routes redistributed to OSPF."
    ::= { f3VrfOspfRouterEntry 8 }

f3VrfOspfRouterBgpRoutesMetric OBJECT-TYPE
    SYNTAX  Unsigned32
    MAX-ACCESS  read-write
    STATUS  current
    DESCRIPTION
        "Metric value of the BGP routes redistributed to OSPF."
    ::= { f3VrfOspfRouterEntry 9 }

f3VrfOspfRouterStaticRoutesRedistributeToOspf OBJECT-TYPE
    SYNTAX  TruthValue
    MAX-ACCESS  read-write
    STATUS  current
    DESCRIPTION
        "This attribute is used to control redistribution of static routes into OSPF."
    ::= { f3VrfOspfRouterEntry 10 }

f3VrfOspfRouterStaticRoutesMetricType OBJECT-TYPE
    SYNTAX  RoutesMetricType
    MAX-ACCESS  read-write
    STATUS  current
    DESCRIPTION
        "Metric type of the static routes redistributed to OSPF."
    ::= { f3VrfOspfRouterEntry 11 }

f3VrfOspfRouterStaticRoutesMetric OBJECT-TYPE
    SYNTAX  Unsigned32
    MAX-ACCESS  read-write
    STATUS  current
    DESCRIPTION
        "Metric value of the static routes redistributed to OSPF."
    ::= { f3VrfOspfRouterEntry 12 }

f3VrfOspfRouterConnectedRoutesRedistributeToOspf OBJECT-TYPE
    SYNTAX  TruthValue
    MAX-ACCESS  read-write
    STATUS  current
    DESCRIPTION
        "This attribute is used to control redistribution of connected routes into OSPF."
    ::= { f3VrfOspfRouterEntry 13 }

f3VrfOspfRouterConnectedRoutesMetricType OBJECT-TYPE
    SYNTAX  RoutesMetricType
    MAX-ACCESS  read-write
    STATUS  current
    DESCRIPTION
        "Metric type of the connected routes redistributed to OSPF."
    ::= { f3VrfOspfRouterEntry 14 }

f3VrfOspfRouterConnectedRoutesMetric OBJECT-TYPE
    SYNTAX  Unsigned32
    MAX-ACCESS  read-write
    STATUS  current
    DESCRIPTION
        "Metric value of the connected routes redistributed to OSPF."
    ::= { f3VrfOspfRouterEntry 15 }

f3VrfOspfRouterDhcpRoutesRedistributeToOspf OBJECT-TYPE
    SYNTAX  TruthValue
    MAX-ACCESS  read-write
    STATUS  current
    DESCRIPTION
        "This attribute is used to control redistribution of dynamic routes learnt 
         via DHCP into OSPF."
    ::= { f3VrfOspfRouterEntry 16 }

f3VrfOspfRouterDhcpRoutesMetricType OBJECT-TYPE
    SYNTAX  RoutesMetricType
    MAX-ACCESS  read-write
    STATUS  current
    DESCRIPTION
        "Metric type of the DHCP routes redistributed to OSPF."
    ::= { f3VrfOspfRouterEntry 17 }

f3VrfOspfRouterDhcpRoutesMetric OBJECT-TYPE
    SYNTAX  Unsigned32
    MAX-ACCESS  read-write
    STATUS  current
    DESCRIPTION
        "Metric value of the DHCP routes redistributed to OSPF."
    ::= { f3VrfOspfRouterEntry 18 }

f3VrfOspfRouterIsAbr OBJECT-TYPE
    SYNTAX  TruthValue
    MAX-ACCESS  read-only
    STATUS  current
    DESCRIPTION
        "."
    ::= { f3VrfOspfRouterEntry 19 }

f3VrfOspfRouterIsAsbr OBJECT-TYPE
    SYNTAX  TruthValue
    MAX-ACCESS  read-only
    STATUS  current
    DESCRIPTION
        "."
    ::= { f3VrfOspfRouterEntry 20 }

f3VrfOspfRouterStorageType OBJECT-TYPE
    SYNTAX      StorageType
    MAX-ACCESS  read-create
    STATUS      current
    DESCRIPTION
        "The storage type for this conceptual row."
   ::= { f3VrfOspfRouterEntry 21 }

f3VrfOspfRouterRowStatus OBJECT-TYPE
    SYNTAX      RowStatus
    MAX-ACCESS  read-create
    STATUS      current
    DESCRIPTION
        "The status of this row.  An entry MUST NOT exist in the 
        active state unless all objects in the entry have an 
        appropriate value, as described
        in the description clause for each writable object.

        The values of f3VrfOspfRouterRowStatus supported are
        createAndGo(4) and destroy(6).  All mandatory attributes
        must be specified in a single SNMP SET request with
        f3VrfOspfRouterRowStatus value as createAndGo(4).
        Upon successful row creation, this object has a
        value of active(1).

        The f3VrfOspfRouterRowStatus object may be modified if
        the associated instance of this object is equal to active(1)."
   ::= { f3VrfOspfRouterEntry 22 }

f3VrfOspfRouterAction OBJECT-TYPE
    SYNTAX      OspfRouterActionType
    MAX-ACCESS  read-write
    STATUS      current
    DESCRIPTION
        "The Ospf Router action."
   ::= { f3VrfOspfRouterEntry 23 }

f3VrfOspfRouterVersion OBJECT-TYPE
    SYNTAX      OspfVersion
    MAX-ACCESS  read-write
    STATUS      current
    DESCRIPTION
        "The version of the Ospf Router."
   ::= { f3VrfOspfRouterEntry 24 }

f3VrfOspfRouterAdministrativeDistance OBJECT-TYPE
    SYNTAX      Unsigned32
    MAX-ACCESS  read-write
    STATUS      current
    DESCRIPTION
        "The Administrative Distance of the Ospf Router."
   ::= { f3VrfOspfRouterEntry 25 }

f3VrfOspfRouterSlaacRoutesRedistributeToOspf OBJECT-TYPE
    SYNTAX  TruthValue
    MAX-ACCESS  read-write
    STATUS  current
    DESCRIPTION
        "This attribute is used to control redistribution of dynamic routes learnt 
         via SLAAC into OSPF."
    ::= { f3VrfOspfRouterEntry 26 }

f3VrfOspfRouterSlaacRoutesMetricType OBJECT-TYPE
    SYNTAX  RoutesMetricType
    MAX-ACCESS  read-write
    STATUS  current
    DESCRIPTION
        "Metric type of the SLAAC routes redistributed to OSPF."
    ::= { f3VrfOspfRouterEntry 27 }

f3VrfOspfRouterSlaacRoutesMetric OBJECT-TYPE
    SYNTAX  Unsigned32
    MAX-ACCESS  read-write
    STATUS  current
    DESCRIPTION
        "Metric value of the SLAAC routes redistributed to OSPF."
    ::= { f3VrfOspfRouterEntry 28 }

f3VrfOspfRouterEcmpMaximumPaths OBJECT-TYPE
    SYNTAX  Unsigned32
    MAX-ACCESS  read-write
    STATUS  current
    DESCRIPTION
        "The maximum number of path used in ECMP for OSPF routes."
    ::= { f3VrfOspfRouterEntry 29 }

f3VrfOspfRouterSrControl OBJECT-TYPE
    SYNTAX  TruthValue
    MAX-ACCESS  read-write
    STATUS  current
    DESCRIPTION
        "Segment Routing Control."
    ::= { f3VrfOspfRouterEntry 30 }

f3VrfOspfRouterConvergenceTime OBJECT-TYPE
    SYNTAX  Unsigned32
    MAX-ACCESS  read-write
    STATUS  current
    DESCRIPTION
        "Convergence Time."
    ::= { f3VrfOspfRouterEntry 31 }

--
-- L3 Traffic OSPF Area
--

f3L3TrafficOspfAreaTable OBJECT-TYPE
    SYNTAX      SEQUENCE OF F3L3TrafficOspfAreaEntry
    MAX-ACCESS  not-accessible
    STATUS      current
    DESCRIPTION
        "Traffic OSPF Area."

   ::= { f3L3Objects 18 }

f3L3TrafficOspfAreaEntry OBJECT-TYPE
    SYNTAX      F3L3TrafficOspfAreaEntry
    MAX-ACCESS  not-accessible
    STATUS      current
    DESCRIPTION
        "A conceptual row in f3L3TrafficOspfAreaTable."
    INDEX   { neIndex, 
              f3VrfIndex,
              f3VrfOspfRouterIndex,
              f3L3TrafficOspfAreaIndex }

   ::= { f3L3TrafficOspfAreaTable 1 }

F3L3TrafficOspfAreaEntry ::= SEQUENCE {
    f3L3TrafficOspfAreaIndex                 Unsigned32,
    f3L3TrafficOspfAreaType                  TrafficOspfAreaType,
    f3L3TrafficOspfAreaDefaultCost           Unsigned32,
    f3L3TrafficOspfAreaId                    IpAddress,
    f3L3TrafficOspfAreaStorageType           StorageType,
    f3L3TrafficOspfAreaRowStatus             RowStatus,
    f3L3TrafficOspfAreaAuthType              OspfAuthType,
    f3L3TrafficOspfAreaSimpleAuthKey         DisplayString,
    f3L3TrafficOspfAreaCryptoKeyId           VariablePointer
}

f3L3TrafficOspfAreaIndex OBJECT-TYPE
    SYNTAX      Unsigned32
    MAX-ACCESS  not-accessible
    STATUS      current
    DESCRIPTION
        "The ID of OSPF Area instance."
   ::= { f3L3TrafficOspfAreaEntry 1 }

f3L3TrafficOspfAreaType OBJECT-TYPE
    SYNTAX      TrafficOspfAreaType
    MAX-ACCESS  read-write
    STATUS      current
    DESCRIPTION
        "OSPF Area Type."
   ::= { f3L3TrafficOspfAreaEntry 2 }

f3L3TrafficOspfAreaDefaultCost OBJECT-TYPE
    SYNTAX      Unsigned32
    MAX-ACCESS  read-write
    STATUS      current
    DESCRIPTION
        "The cost of a default route propagated to stub area."
   ::= { f3L3TrafficOspfAreaEntry 3 }

f3L3TrafficOspfAreaId OBJECT-TYPE
    SYNTAX      IpAddress
    MAX-ACCESS  read-write
    STATUS      current
    DESCRIPTION
        "The 32-bit number identifying the area."
   ::= { f3L3TrafficOspfAreaEntry 4 }

f3L3TrafficOspfAreaStorageType OBJECT-TYPE
    SYNTAX      StorageType
    MAX-ACCESS  read-create
    STATUS      current
    DESCRIPTION
        "The storage type for this conceptual row."
   ::= { f3L3TrafficOspfAreaEntry 5 }

f3L3TrafficOspfAreaRowStatus OBJECT-TYPE
    SYNTAX      RowStatus
    MAX-ACCESS  read-create
    STATUS      current
    DESCRIPTION
        "The status of this row.  An entry MUST NOT exist in the 
        active state unless all objects in the entry have an 
        appropriate value, as described
        in the description clause for each writable object.

        The values of f3L3TrafficOspfAreaRowStatus supported are
        createAndGo(4) and destroy(6).  All mandatory attributes
        must be specified in a single SNMP SET request with
        f3L3TrafficOspfAreaRowStatus value as createAndGo(4).
        Upon successful row creation, this object has a
        value of active(1).

        The f3L3TrafficOspfAreaRowStatus object may be modified if
        the associated instance of this object is equal to active(1)."
   ::= { f3L3TrafficOspfAreaEntry 6 }

f3L3TrafficOspfAreaAuthType OBJECT-TYPE
    SYNTAX      OspfAuthType
    MAX-ACCESS  read-write
    STATUS      current
    DESCRIPTION
        "This attribute is used to specify authentication type."
   ::= { f3L3TrafficOspfAreaEntry 7 }

f3L3TrafficOspfAreaSimpleAuthKey OBJECT-TYPE
    SYNTAX      DisplayString
    MAX-ACCESS  read-write
    STATUS      current
    DESCRIPTION
        "The attribute is used to specify simple authentication key."
    ::= { f3L3TrafficOspfAreaEntry 8 }

f3L3TrafficOspfAreaCryptoKeyId OBJECT-TYPE
     SYNTAX      VariablePointer
     MAX-ACCESS  read-write
     STATUS      current
     DESCRIPTION
        "Authentication Key Id."
    ::= { f3L3TrafficOspfAreaEntry 9 }

--
-- L3 Traffic OSPF Area Interface Member List
--

f3L3TrafficOspfAreaIfMemberTable OBJECT-TYPE
    SYNTAX      SEQUENCE OF F3L3TrafficOspfAreaIfMemberEntry
    MAX-ACCESS  not-accessible
    STATUS      current
    DESCRIPTION
        "OSPF Area Interface Member."

   ::= { f3L3Objects 19 }

f3L3TrafficOspfAreaIfMemberEntry OBJECT-TYPE
    SYNTAX      F3L3TrafficOspfAreaIfMemberEntry
    MAX-ACCESS  not-accessible
    STATUS      current
    DESCRIPTION
        "A conceptual row in f3L3TrafficOspfAreaIfMemberTable."
    INDEX   { neIndex, 
              f3VrfIndex,
              f3VrfOspfRouterIndex,
              f3L3TrafficOspfAreaIndex,
              f3L3TrafficOspfAreaIfMemberObject }

   ::= { f3L3TrafficOspfAreaIfMemberTable 1 }

F3L3TrafficOspfAreaIfMemberEntry ::= SEQUENCE {
    f3L3TrafficOspfAreaIfMemberObject         VariablePointer,
    f3L3TrafficOspfAreaIfMemberStorageType    StorageType,
    f3L3TrafficOspfAreaIfMemberRowStatus      RowStatus
}

f3L3TrafficOspfAreaIfMemberObject    OBJECT-TYPE
    SYNTAX      VariablePointer
    MAX-ACCESS  not-accessible
    STATUS      current
    DESCRIPTION
         "OSPF Area Interface Member."
     ::= { f3L3TrafficOspfAreaIfMemberEntry 1 }

f3L3TrafficOspfAreaIfMemberStorageType OBJECT-TYPE
    SYNTAX      StorageType
    MAX-ACCESS  read-create
    STATUS      current
    DESCRIPTION
        "The storage type for this conceptual row."
   ::= { f3L3TrafficOspfAreaIfMemberEntry 2 }

f3L3TrafficOspfAreaIfMemberRowStatus OBJECT-TYPE
    SYNTAX      RowStatus
    MAX-ACCESS  read-create
    STATUS      current
    DESCRIPTION
        "The status of this row.  An entry MUST NOT exist in the 
        active state unless all objects in the entry have an 
        appropriate value, as described
        in the description clause for each writable object.

        The values of f3L3TrafficOspfAreaIfMemberRowStatus supported are
        createAndGo(4) and destroy(6).  All mandatory attributes
        must be specified in a single SNMP SET request with
        f3L3TrafficOspfAreaIfMemberRowStatus value as createAndGo(4).
        Upon successful row creation, this object has a
        value of active(1).

        The f3L3TrafficOspfAreaIfMemberRowStatus object may be modified if
        the associated instance of this object is equal to active(1)."
   ::= { f3L3TrafficOspfAreaIfMemberEntry 3 }


--
-- VRF Loopback Interface
--

f3VrfLoopbackInterfaceTable OBJECT-TYPE
    SYNTAX      SEQUENCE OF F3VrfLoopbackInterfaceEntry
    MAX-ACCESS  not-accessible
    STATUS      current
    DESCRIPTION
        "."

   ::= { f3L3Objects 20 }

f3VrfLoopbackInterfaceEntry OBJECT-TYPE
    SYNTAX      F3VrfLoopbackInterfaceEntry
    MAX-ACCESS  not-accessible
    STATUS      current
    DESCRIPTION
        "A conceptual row in f3VrfLoopbackInterfaceTable."
    INDEX   { neIndex, 
              f3VrfIndex,
              f3VrfLoopbackInterfaceIndex }

   ::= { f3VrfLoopbackInterfaceTable 1 }

F3VrfLoopbackInterfaceEntry ::= SEQUENCE {
    f3VrfLoopbackInterfaceIndex                  Unsigned32,
    f3VrfLoopbackInterfaceName                   DisplayString,
    f3VrfLoopbackInterfaceIpAddress              IpAddress,
    f3VrfLoopbackInterfaceNetMask                IpAddress,
    f3VrfLoopbackInterfaceCIRLo                  Unsigned32,
    f3VrfLoopbackInterfaceCIRHi                  Unsigned32,
    f3VrfLoopbackInterfaceStorageType            StorageType,
    f3VrfLoopbackInterfaceRowStatus              RowStatus,
    f3VrfLoopbackInterfaceIpMode                 IpMode,
    f3VrfLoopbackInterfaceIpv6Address            Ipv6Address,
    f3VrfLoopbackInterfaceIpv6AddrPrefixLen      Integer32
}

f3VrfLoopbackInterfaceIndex OBJECT-TYPE
    SYNTAX      Unsigned32
    MAX-ACCESS  not-accessible
    STATUS      current
    DESCRIPTION
        "."
   ::= { f3VrfLoopbackInterfaceEntry 1 }

f3VrfLoopbackInterfaceName    OBJECT-TYPE
    SYNTAX      DisplayString (SIZE(0..15))
    MAX-ACCESS  read-write
    STATUS      current
    DESCRIPTION
         "."
     ::= { f3VrfLoopbackInterfaceEntry 2 }

f3VrfLoopbackInterfaceIpAddress OBJECT-TYPE
    SYNTAX      IpAddress 
    MAX-ACCESS  read-write
    STATUS      current
    DESCRIPTION
         "."
    ::= { f3VrfLoopbackInterfaceEntry 3 }

f3VrfLoopbackInterfaceNetMask OBJECT-TYPE
    SYNTAX      IpAddress 
    MAX-ACCESS  read-write
    STATUS      current
    DESCRIPTION
         "."
    ::= { f3VrfLoopbackInterfaceEntry 4 }

f3VrfLoopbackInterfaceCIRLo OBJECT-TYPE
    SYNTAX      Unsigned32 
    MAX-ACCESS  read-write
    STATUS      current
    DESCRIPTION
         "."
    ::= { f3VrfLoopbackInterfaceEntry 5 }
    
f3VrfLoopbackInterfaceCIRHi OBJECT-TYPE
    SYNTAX      Unsigned32 
    MAX-ACCESS  read-write
    STATUS      current
    DESCRIPTION
         "."
    ::= { f3VrfLoopbackInterfaceEntry 6 }
    
f3VrfLoopbackInterfaceStorageType OBJECT-TYPE
    SYNTAX      StorageType
    MAX-ACCESS  read-create
    STATUS      current
    DESCRIPTION
        "The storage type for this conceptual row."
   ::= { f3VrfLoopbackInterfaceEntry 7 }

f3VrfLoopbackInterfaceRowStatus OBJECT-TYPE
    SYNTAX      RowStatus
    MAX-ACCESS  read-create
    STATUS      current
    DESCRIPTION
        "The status of this row.  An entry MUST NOT exist in the 
        active state unless all objects in the entry have an 
        appropriate value, as described
        in the description clause for each writable object.

        The values of f3VrfLoopbackInterfaceRowStatus supported are
        createAndGo(4) and destroy(6).  All mandatory attributes
        must be specified in a single SNMP SET request with
        f3VrfLoopbackInterfaceRowStatus value as createAndGo(4).
        Upon successful row creation, this object has a
        value of active(1).

        The f3VrfLoopbackInterfaceRowStatus object may be modified if
        the associated instance of this object is equal to active(1)."
   ::= { f3VrfLoopbackInterfaceEntry 8 }

f3VrfLoopbackInterfaceIpMode OBJECT-TYPE
    SYNTAX     IpMode 
    MAX-ACCESS read-write
    STATUS   current
    DESCRIPTION
       "This object means the ip mode for the interface."
    ::= { f3VrfLoopbackInterfaceEntry 9 }

f3VrfLoopbackInterfaceIpv6Address OBJECT-TYPE
    SYNTAX     Ipv6Address 
    MAX-ACCESS read-write
    STATUS   current
    DESCRIPTION
       "This object means the ipv6 address for the interface."
    ::= { f3VrfLoopbackInterfaceEntry 10 }

f3VrfLoopbackInterfaceIpv6AddrPrefixLen OBJECT-TYPE
    SYNTAX     Integer32 
    MAX-ACCESS read-write
    STATUS   current
    DESCRIPTION
       "This object means the ipv6 address prefix length for the interface."
    ::= { f3VrfLoopbackInterfaceEntry 11 }


--
--  L3 Traffic Ospf AS Link State Database
--

f3L3TrafficOspfAsLsDbTable  OBJECT-TYPE
    SYNTAX      SEQUENCE OF F3L3TrafficOspfAsLsDbEntry
    MAX-ACCESS  not-accessible
    STATUS      current
    DESCRIPTION
            "OSPF AS Link State Database.
             Must set f3VrfOspfRouterAction as optimizeOspfAsLsDbRetrieve(1) before get data from this table."
    ::= { f3L3Objects 21 }

f3L3TrafficOspfAsLsDbEntry OBJECT-TYPE
    SYNTAX      F3L3TrafficOspfAsLsDbEntry 
    MAX-ACCESS  not-accessible
    STATUS      current
    DESCRIPTION
            "A conceptual row in the f3L3TrafficOspfAsLsDbTable. Entries can
            be created/deleted in this table by management application action."
    INDEX { neIndex, 
            f3VrfIndex, 
            f3VrfOspfRouterIndex,
            f3L3TrafficOspfAsLsDbType,
            f3L3TrafficOspfAsLsDbId,
            f3L3TrafficOspfAsLsDbRouterId }
    ::= { f3L3TrafficOspfAsLsDbTable 1 }

F3L3TrafficOspfAsLsDbEntry ::= SEQUENCE {
    f3L3TrafficOspfAsLsDbType                OspfAsLsaType,
    f3L3TrafficOspfAsLsDbId                  IpAddress,
    f3L3TrafficOspfAsLsDbRouterId            IpAddress,
    f3L3TrafficOspfAsLsDbChecksum            Unsigned32,
    f3L3TrafficOspfAsLsDbSeqNum              Unsigned32,
    f3L3TrafficOspfAsLsDbAge                 Unsigned32
}

f3L3TrafficOspfAsLsDbType OBJECT-TYPE
    SYNTAX      OspfAsLsaType
    MAX-ACCESS  not-accessible
    STATUS      current
    DESCRIPTION
        "LSA Type."
   ::= { f3L3TrafficOspfAsLsDbEntry 1 }

f3L3TrafficOspfAsLsDbId OBJECT-TYPE
    SYNTAX      IpAddress
    MAX-ACCESS  not-accessible
    STATUS      current
    DESCRIPTION
        "Link State ID."
   ::= { f3L3TrafficOspfAsLsDbEntry 2 }

f3L3TrafficOspfAsLsDbRouterId OBJECT-TYPE
    SYNTAX      IpAddress
    MAX-ACCESS  not-accessible
    STATUS      current
    DESCRIPTION
        "LSA advertising router."
   ::= { f3L3TrafficOspfAsLsDbEntry 3 }

f3L3TrafficOspfAsLsDbChecksum OBJECT-TYPE
    SYNTAX      Unsigned32
    MAX-ACCESS  read-only
    STATUS      current
    DESCRIPTION
        "The checksum associated with Link State Advertisement."
   ::= { f3L3TrafficOspfAsLsDbEntry 4 }

f3L3TrafficOspfAsLsDbSeqNum OBJECT-TYPE
    SYNTAX      Unsigned32
    MAX-ACCESS  read-only
    STATUS      current
    DESCRIPTION
        "The Sequence Number associated with the last LSA."
   ::= { f3L3TrafficOspfAsLsDbEntry 5 }

f3L3TrafficOspfAsLsDbAge OBJECT-TYPE
    SYNTAX      Unsigned32
    MAX-ACCESS  read-only
    STATUS      current
    DESCRIPTION
        "The age, in seconds, since this LSA was last received."
   ::= { f3L3TrafficOspfAsLsDbEntry 6 }


--
--  L3 Traffic Ospf Link State Database
--

f3L3TrafficOspfLsDbTable  OBJECT-TYPE
    SYNTAX      SEQUENCE OF F3L3TrafficOspfLsDbEntry
    MAX-ACCESS  not-accessible
    STATUS      current
    DESCRIPTION
            "OSPF Link State database.
             Must set f3VrfOspfRouterAction as optimizeOspfLsDbRetrieve(2) before get data from this table."
    ::= { f3L3Objects 22 }

f3L3TrafficOspfLsDbEntry OBJECT-TYPE
    SYNTAX      F3L3TrafficOspfLsDbEntry 
    MAX-ACCESS  not-accessible
    STATUS      current
    DESCRIPTION
            "A conceptual row in the f3L3TrafficOspfLsDbTable. Entries can
            be created/deleted in this table by management application action."
    INDEX { neIndex, 
            f3VrfIndex, 
            f3VrfOspfRouterIndex,
            f3L3TrafficOspfLsDbType,
            f3L3TrafficOspfLsDbId,
            f3L3TrafficOspfLsDbRouterId,
            f3L3TrafficOspfLsDbAreaId }
    ::= { f3L3TrafficOspfLsDbTable 1 }

F3L3TrafficOspfLsDbEntry ::= SEQUENCE {
    f3L3TrafficOspfLsDbType                OspfLsaType,
    f3L3TrafficOspfLsDbId                  IpAddress,
    f3L3TrafficOspfLsDbRouterId            IpAddress,
    f3L3TrafficOspfLsDbAreaId              IpAddress,
    f3L3TrafficOspfLsDbChecksum            Unsigned32,
    f3L3TrafficOspfLsDbSeqNum              Unsigned32,
    f3L3TrafficOspfLsDbAge                 Unsigned32
}

f3L3TrafficOspfLsDbType OBJECT-TYPE
    SYNTAX      OspfLsaType
    MAX-ACCESS  not-accessible
    STATUS      current
    DESCRIPTION
        "LSA Type."
   ::= { f3L3TrafficOspfLsDbEntry 1 }

f3L3TrafficOspfLsDbId OBJECT-TYPE
    SYNTAX      IpAddress
    MAX-ACCESS  not-accessible
    STATUS      current
    DESCRIPTION
        "Link State ID."
   ::= { f3L3TrafficOspfLsDbEntry 2 }

f3L3TrafficOspfLsDbRouterId OBJECT-TYPE
    SYNTAX      IpAddress
    MAX-ACCESS  not-accessible
    STATUS      current
    DESCRIPTION
        "Advertising Router ID."
   ::= { f3L3TrafficOspfLsDbEntry 3 }
   
f3L3TrafficOspfLsDbAreaId OBJECT-TYPE
    SYNTAX      IpAddress
    MAX-ACCESS  not-accessible
    STATUS      current
    DESCRIPTION
        "Area ID."
   ::= { f3L3TrafficOspfLsDbEntry 4 }

f3L3TrafficOspfLsDbChecksum OBJECT-TYPE
    SYNTAX      Unsigned32
    MAX-ACCESS  read-only
    STATUS      current
    DESCRIPTION
        "The checksum associated with Link State Advertisement."
   ::= { f3L3TrafficOspfLsDbEntry 5 }

f3L3TrafficOspfLsDbSeqNum OBJECT-TYPE
    SYNTAX      Unsigned32
    MAX-ACCESS  read-only
    STATUS      current
    DESCRIPTION
        "The Sequence Number associated with the last LSA."
   ::= { f3L3TrafficOspfLsDbEntry 6 }

f3L3TrafficOspfLsDbAge OBJECT-TYPE
    SYNTAX      Unsigned32
    MAX-ACCESS  read-only
    STATUS      current
    DESCRIPTION
        "The age, in seconds, since this LSA was last received."
   ::= { f3L3TrafficOspfLsDbEntry 7 }


--
--  L3 Traffic Ospf Neighbor
--

f3L3TrafficOspfNeighborTable  OBJECT-TYPE
    SYNTAX      SEQUENCE OF F3L3TrafficOspfNeighborEntry
    MAX-ACCESS  not-accessible
    STATUS      current
    DESCRIPTION
            "OSPF neighbor table.
             Must set f3VrfOspfRouterAction as optimizeOspfNeighborRetrieve(3) before get data from this table."
    ::= { f3L3Objects 23 }

f3L3TrafficOspfNeighborEntry OBJECT-TYPE
    SYNTAX      F3L3TrafficOspfNeighborEntry 
    MAX-ACCESS  not-accessible
    STATUS      current
    DESCRIPTION
            "A conceptual row in the f3L3TrafficOspfNeighborTable. Entries can
            be created/deleted in this table by management application action."
    INDEX { neIndex, 
            f3VrfIndex,
            f3VrfOspfRouterIndex,
            f3L3TrafficOspfNeighborIpAddress }
    ::= { f3L3TrafficOspfNeighborTable 1 }

F3L3TrafficOspfNeighborEntry ::= SEQUENCE {
    f3L3TrafficOspfNeighborIpAddress                IpAddress,
    f3L3TrafficOspfNeighborInterface                VariablePointer,
    f3L3TrafficOspfNeighborRouterId                 IpAddress,
    f3L3TrafficOspfNeighborState                    OspfAdjacencyState,
    f3L3TrafficOspfNeighborRole                     TrafficOspfRole,
    f3L3TrafficOspfNeighborPriority                 Unsigned32,
    f3L3TrafficOspfNeighborDeadTime                 Unsigned32,
    f3L3TrafficOspfNeighborLocalInterfaceName       DisplayString
}

f3L3TrafficOspfNeighborIpAddress OBJECT-TYPE
    SYNTAX      IpAddress
    MAX-ACCESS  not-accessible
    STATUS      current
    DESCRIPTION
        "Address of interface of neighbor."
   ::= { f3L3TrafficOspfNeighborEntry 1 }

f3L3TrafficOspfNeighborInterface OBJECT-TYPE
    SYNTAX      VariablePointer
    MAX-ACCESS  read-only
    STATUS      deprecated
    DESCRIPTION
        "The local interface which discovers the neighbor."
   ::= { f3L3TrafficOspfNeighborEntry 2 }

f3L3TrafficOspfNeighborRouterId OBJECT-TYPE
    SYNTAX      IpAddress
    MAX-ACCESS  read-only
    STATUS      current
    DESCRIPTION
        "Router ID of the neighbor."
   ::= { f3L3TrafficOspfNeighborEntry 3 }

f3L3TrafficOspfNeighborState OBJECT-TYPE
    SYNTAX      OspfAdjacencyState
    MAX-ACCESS  read-only
    STATUS      current
    DESCRIPTION
        "State of Link State Database synchronization with the neighbor."
   ::= { f3L3TrafficOspfNeighborEntry 4 }

f3L3TrafficOspfNeighborRole OBJECT-TYPE
    SYNTAX      TrafficOspfRole
    MAX-ACCESS  read-only
    STATUS      current
    DESCRIPTION
        "Role of the neighbor. DR, DR other and Backup are applicable."
   ::= { f3L3TrafficOspfNeighborEntry 5 }

f3L3TrafficOspfNeighborPriority OBJECT-TYPE
    SYNTAX      Unsigned32
    MAX-ACCESS  read-only
    STATUS      current
    DESCRIPTION
        "The priority of the neighbor."
   ::= { f3L3TrafficOspfNeighborEntry 6 }

f3L3TrafficOspfNeighborDeadTime OBJECT-TYPE
    SYNTAX      Unsigned32
    MAX-ACCESS  read-only
    STATUS      current
    DESCRIPTION
        "The Dead Time field indicates the amount of time remaining that 
         the router waits to receive an OSPF hello packet from the 
         neighbor before declaring the neighbor down."
   ::= { f3L3TrafficOspfNeighborEntry 7 }

f3L3TrafficOspfNeighborLocalInterfaceName OBJECT-TYPE
    SYNTAX      DisplayString
    MAX-ACCESS  read-only
    STATUS      current
    DESCRIPTION
        "The name of local interface which discovers the neighbor."
   ::= { f3L3TrafficOspfNeighborEntry 8 }

--
--  L3 traffic ip interface Ospf Table
--

f3L3TrafficIPInterfaceOspfTable  OBJECT-TYPE
    SYNTAX      SEQUENCE OF F3L3TrafficIPInterfaceOspfEntry
    MAX-ACCESS  not-accessible
    STATUS      current
    DESCRIPTION
            "OSPF Traffic IP Interface Attributes."
    ::= { f3L3Objects 25 }

f3L3TrafficIPInterfaceOspfEntry  OBJECT-TYPE
    SYNTAX      F3L3TrafficIPInterfaceOspfEntry
    MAX-ACCESS  not-accessible
    STATUS      current
    DESCRIPTION
            "A conceptual row in the f3L3TrafficIPInterfaceOspfTable."
    AUGMENTS { f3L3TrafficIPInterfaceEntry }
    ::= { f3L3TrafficIPInterfaceOspfTable 1 }

F3L3TrafficIPInterfaceOspfEntry ::= SEQUENCE {
    f3L3TrafficIPIfOspfAreaId                          IpAddress,
    f3L3TrafficIPIfOspfCost                            Unsigned32,
    f3L3TrafficIPIfOspfIfType                          OspfIfType,
    f3L3TrafficIPIfOspfRtrPriority                     Unsigned32,
    f3L3TrafficIPIfOspfHelloInterval                   Unsigned32,
    f3L3TrafficIPIfOspfDeadInterval                    Unsigned32,
    f3L3TrafficIPIfOspfTransmitDelay                   Unsigned32,
    f3L3TrafficIPIfOspfRetransmitInterval              Unsigned32,
    f3L3TrafficIPIfOspfState                           OspfInterfaceState,
    f3L3TrafficIPIfOspfDesignatedRouterId              IpAddress,
    f3L3TrafficIPIfOspfBackupDesignatedRouterId        IpAddress,
    f3L3TrafficIPIfOspfAuthType                        OspfAuthType,
    f3L3TrafficIPIfOspfSimpleAuthKey                   DisplayString,
    f3L3TrafficIPIfospfCryptoKeyId                     VariablePointer
}

f3L3TrafficIPIfOspfAreaId    OBJECT-TYPE
    SYNTAX      IpAddress
    MAX-ACCESS  read-only
    STATUS      current
    DESCRIPTION
         "A 32-bit number identifying the area."
     ::= { f3L3TrafficIPInterfaceOspfEntry 1 }

f3L3TrafficIPIfOspfCost    OBJECT-TYPE
    SYNTAX      Unsigned32
    MAX-ACCESS  read-write
    STATUS      current
    DESCRIPTION
         "The cost of the route during the SPF calculation."
     ::= { f3L3TrafficIPInterfaceOspfEntry 2 }

f3L3TrafficIPIfOspfIfType    OBJECT-TYPE
    SYNTAX      OspfIfType
    MAX-ACCESS  read-write
    STATUS      current
    DESCRIPTION
         "Interface network type."
     ::= { f3L3TrafficIPInterfaceOspfEntry 3 }

f3L3TrafficIPIfOspfRtrPriority    OBJECT-TYPE
    SYNTAX      Unsigned32
    MAX-ACCESS  read-write
    STATUS      current
    DESCRIPTION
         "An 8-bit unsigned integer, used for DR and BDR election, 
          may be default. 0 means not to attend DR election."
     ::= { f3L3TrafficIPInterfaceOspfEntry 4 }

f3L3TrafficIPIfOspfHelloInterval    OBJECT-TYPE
    SYNTAX      Unsigned32
    MAX-ACCESS  read-write
    STATUS      current
    DESCRIPTION
         "The interval in seconds between Hello Packets that 
          the router sends on the interface."
     ::= { f3L3TrafficIPInterfaceOspfEntry 5 }

f3L3TrafficIPIfOspfDeadInterval    OBJECT-TYPE
    SYNTAX      Unsigned32
    MAX-ACCESS  read-write
    STATUS      current
    DESCRIPTION
         "The number of seconds before the router's neighbors will 
          declare it down, when they stop hearing the router's Hello Packets."
     ::= { f3L3TrafficIPInterfaceOspfEntry 6 }

f3L3TrafficIPIfOspfTransmitDelay    OBJECT-TYPE
    SYNTAX      Unsigned32
    MAX-ACCESS  read-write
    STATUS      current
    DESCRIPTION
         "2~65535 Default 2s The estimated number of seconds it takes to
          transmit a Link State Update Packet over this interface. 
          LSAs contained in the Link State update packet will have their 
          age incremented by this amount before transmission. This value 
          should take into account transmission and propagation delays; 
          it must be greater than 1."
     ::= { f3L3TrafficIPInterfaceOspfEntry 7 }

f3L3TrafficIPIfOspfRetransmitInterval    OBJECT-TYPE
    SYNTAX      Unsigned32
    MAX-ACCESS  read-write
    STATUS      current
    DESCRIPTION
         "The number of seconds between LSA retransmissions, for adjacencies 
          belonging to this interface. Also used when retransmitting 
          Database Description and Link State Request Packets."
     ::= { f3L3TrafficIPInterfaceOspfEntry 8 }

f3L3TrafficIPIfOspfState    OBJECT-TYPE
    SYNTAX      OspfInterfaceState
    MAX-ACCESS  read-only
    STATUS      current
    DESCRIPTION
         "OSPF Interface state."
     ::= { f3L3TrafficIPInterfaceOspfEntry 9 }

f3L3TrafficIPIfOspfDesignatedRouterId    OBJECT-TYPE
    SYNTAX      IpAddress
    MAX-ACCESS  read-only
    STATUS      current
    DESCRIPTION
         "Designated Router IP interface on the Network."
     ::= { f3L3TrafficIPInterfaceOspfEntry 10 }

f3L3TrafficIPIfOspfBackupDesignatedRouterId    OBJECT-TYPE
    SYNTAX      IpAddress
    MAX-ACCESS  read-only
    STATUS      current
    DESCRIPTION
         "Backup Designated Router IP interface on the Network."
     ::= { f3L3TrafficIPInterfaceOspfEntry 11 }

f3L3TrafficIPIfOspfAuthType    OBJECT-TYPE
    SYNTAX      OspfAuthType
    MAX-ACCESS  read-write
    STATUS      current
    DESCRIPTION
         "This attribute is used to specify authentication type. 
          Simple: 64-bits clear password inserted into OSPF packets header.
          None: No authentication is used.
          Cryptographic: a shared secret which enables the generation/verification 
          of message digests which are appended to the OSPF protocol packets."
     ::= { f3L3TrafficIPInterfaceOspfEntry 12 }

f3L3TrafficIPIfOspfSimpleAuthKey    OBJECT-TYPE
    SYNTAX      DisplayString
    MAX-ACCESS  read-write
    STATUS      current
    DESCRIPTION
         "Authentication key."
     ::= { f3L3TrafficIPInterfaceOspfEntry 13 }

f3L3TrafficIPIfospfCryptoKeyId    OBJECT-TYPE
    SYNTAX      VariablePointer
    MAX-ACCESS  read-write
    STATUS      current
    DESCRIPTION
         "Crypto key Id."
     ::= { f3L3TrafficIPInterfaceOspfEntry 14 }



--
--  L3 traffic ipv6 interface Table
--

f3L3TrafficIPv6InterfaceTable  OBJECT-TYPE
    SYNTAX      SEQUENCE OF F3L3TrafficIPv6InterfaceEntry
    MAX-ACCESS  not-accessible
    STATUS      current
    DESCRIPTION
            "A list of entries for the L3 Traffic IPv6 Interface."
    ::= { f3L3Objects 26 }

f3L3TrafficIPv6InterfaceEntry  OBJECT-TYPE
    SYNTAX      F3L3TrafficIPv6InterfaceEntry
    MAX-ACCESS  not-accessible
    STATUS      current
    DESCRIPTION
            "A conceptual row in the f3L3TrafficIPv6InterfaceTable."
    INDEX { neIndex, shelfIndex, slotIndex,
            f3L3FlowPointPortIndex, f3L3FlowPointIndex, f3L3TrafficIPv6IfIndex }
    ::= { f3L3TrafficIPv6InterfaceTable 1 }

F3L3TrafficIPv6InterfaceEntry ::= SEQUENCE {
    f3L3TrafficIPv6IfIndex                               Integer32,
    f3L3TrafficIPv6IfName                                DisplayString,
    f3L3TrafficIPv6IfAdminState                          AdminState,
    f3L3TrafficIPv6IfSecondaryState                      SecondaryState,
    f3L3TrafficIPv6IfOperationalState                    OperationalState,
    f3L3TrafficIPv6IfType                                IpInterfaceType,
    f3L3TrafficIPv6IfLinkLocalAddr                       Ipv6Address,
    f3L3TrafficIPv6IfLinkLocalAddrMode                   Ipv6LinkLocalAddressMode,
    f3L3TrafficIPv6IfMtu                                 Integer32,
    f3L3TrafficIPv6IfStatelessAddrAutoconfigEnabled      TruthValue,
    f3L3TrafficIPv6IfDefaultGateway                      Ipv6Address,
    f3L3TrafficIPv6IfIcmpErrorMsgRateLimit               Integer32,
    f3L3TrafficIPv6IfDhcpRole                            CmDhcpRole,
    f3L3TrafficIPv6IfDhcpEnabled                         TruthValue,
    f3L3TrafficIPv6IfDhcpRapidCommitControlEnabled       TruthValue,
    f3L3TrafficIPv6IfMaxRAInterval                       Unsigned32,
    f3L3TrafficIPv6IfMinRAInterval                       Unsigned32,
    f3L3TrafficIPv6IfRouterLifeTime                      Unsigned32,
    f3L3TrafficIPv6IfReachableTime                       Unsigned32,
    f3L3TrafficIPv6IfRaDhcpMoreConfigEnabled             TruthValue,
    f3L3TrafficIPv6IfRaManagedAddressConfigEnabled       TruthValue,
    f3L3TrafficIPv6IfRaRDNSSOptionEnabled                TruthValue,
    f3L3TrafficIPv6IfRaRDNSSLifeTime                     Unsigned32,
    f3L3TrafficIPv6IfRaDNSSList                          DisplayString,
    f3L3TrafficIPv6IfRaDefaultRouterPreference           NdpRaDefaultRouterPreference,
    f3L3TrafficIPv6IfDupAddrDetectControl                TruthValue,
    f3L3TrafficIPv6IfDupAddrDetectTransmits              Unsigned32,
    f3L3TrafficIPv6IfDupAddrDetectRetransTimer           Unsigned32,
    f3L3TrafficIPv6IfStorageType                         StorageType,
    f3L3TrafficIPv6IfRowStatus                           RowStatus,
    f3L3TrafficIPv6IfAction                              TrafficIpv6InterfaceActionType
}

f3L3TrafficIPv6IfIndex   OBJECT-TYPE
    SYNTAX     Integer32
    MAX-ACCESS not-accessible
    STATUS     current
    DESCRIPTION
       "It specifies the traffic IPv6 interface number."
    ::= { f3L3TrafficIPv6InterfaceEntry 1 }

f3L3TrafficIPv6IfName   OBJECT-TYPE
    SYNTAX     DisplayString (SIZE (0..15))
    MAX-ACCESS read-write
    STATUS     current
    DESCRIPTION
       "It specifies the traffic IPv6 interface name."
    ::= { f3L3TrafficIPv6InterfaceEntry 2 }

f3L3TrafficIPv6IfAdminState OBJECT-TYPE
    SYNTAX      AdminState
    MAX-ACCESS  read-write
    STATUS      current
    DESCRIPTION
           "This object represents the Administrative State of the interface."
    ::= { f3L3TrafficIPv6InterfaceEntry 3 }

f3L3TrafficIPv6IfSecondaryState OBJECT-TYPE
    SYNTAX      SecondaryState
    MAX-ACCESS  read-only
    STATUS      current
    DESCRIPTION
           "This object represents the Secondary State of the interface."
    ::= { f3L3TrafficIPv6InterfaceEntry 4 }

f3L3TrafficIPv6IfOperationalState OBJECT-TYPE
    SYNTAX      OperationalState
    MAX-ACCESS  read-only
    STATUS      current
    DESCRIPTION
           "This object represents the Operational State of the interface."
    ::= { f3L3TrafficIPv6InterfaceEntry 5 }

f3L3TrafficIPv6IfType OBJECT-TYPE
    SYNTAX      IpInterfaceType
    MAX-ACCESS  read-write
    STATUS      current
    DESCRIPTION
           "This object represents the type of the interface."
    ::= { f3L3TrafficIPv6InterfaceEntry 6 }

f3L3TrafficIPv6IfLinkLocalAddr OBJECT-TYPE
    SYNTAX      Ipv6Address
    MAX-ACCESS  read-write
    STATUS      current
    DESCRIPTION
           "Link-local Address."
    ::= { f3L3TrafficIPv6InterfaceEntry 7 }

f3L3TrafficIPv6IfLinkLocalAddrMode OBJECT-TYPE
    SYNTAX      Ipv6LinkLocalAddressMode
    MAX-ACCESS  read-write
    STATUS      current
    DESCRIPTION
           "The assignment mode of IPv6 Link-Local Address, only manual and automatic are applicable."
    ::= { f3L3TrafficIPv6InterfaceEntry 8 }

f3L3TrafficIPv6IfMtu OBJECT-TYPE
    SYNTAX      Integer32
    MAX-ACCESS  read-only
    STATUS      current
    DESCRIPTION
           "This is the MTU for IPv6 Traffic interface."
    ::= { f3L3TrafficIPv6InterfaceEntry 9 }

f3L3TrafficIPv6IfStatelessAddrAutoconfigEnabled OBJECT-TYPE
    SYNTAX      TruthValue
    MAX-ACCESS  read-write
    STATUS      current
    DESCRIPTION
           "This is the control to enable or disable stateless
            address auto configuration."
    ::= { f3L3TrafficIPv6InterfaceEntry 10 }

f3L3TrafficIPv6IfDefaultGateway OBJECT-TYPE
    SYNTAX      Ipv6Address
    MAX-ACCESS  read-write
    STATUS      current
    DESCRIPTION
           "indicates active default GW of the interface."
    ::= { f3L3TrafficIPv6InterfaceEntry 11 }

f3L3TrafficIPv6IfIcmpErrorMsgRateLimit OBJECT-TYPE
    SYNTAX      Integer32
    MAX-ACCESS  read-write
    STATUS      current
    DESCRIPTION
           "limit originated ICMP error messages rate in number of messages per second.
            The value 0xFFFF shall be used to indicate no error message limit."
    ::= { f3L3TrafficIPv6InterfaceEntry 12 }

f3L3TrafficIPv6IfDhcpRole OBJECT-TYPE
    SYNTAX      CmDhcpRole
    MAX-ACCESS  read-write
    STATUS      current
    DESCRIPTION
           "Allows setting the DHCPv6 role on this interface."
    ::= { f3L3TrafficIPv6InterfaceEntry 13 }

f3L3TrafficIPv6IfDhcpEnabled OBJECT-TYPE
    SYNTAX      TruthValue
    MAX-ACCESS  read-write
    STATUS      current
    DESCRIPTION
           "Allows enabling/disabling of DHCPv6 on this interface."
    ::= { f3L3TrafficIPv6InterfaceEntry 14 }

f3L3TrafficIPv6IfDhcpRapidCommitControlEnabled OBJECT-TYPE
    SYNTAX      TruthValue
    MAX-ACCESS  read-write
    STATUS      current
    DESCRIPTION
           "This is the control to enable or disable DHCP rapid commit."
    ::= { f3L3TrafficIPv6InterfaceEntry 15 }

f3L3TrafficIPv6IfMaxRAInterval OBJECT-TYPE
    SYNTAX      Unsigned32
    MAX-ACCESS  read-write
    STATUS      current
    DESCRIPTION
           "Maximum time in seconds between generated RA messages."
    ::= { f3L3TrafficIPv6InterfaceEntry 16 }

f3L3TrafficIPv6IfMinRAInterval OBJECT-TYPE
    SYNTAX      Unsigned32
    MAX-ACCESS  read-write
    STATUS      current
    DESCRIPTION
           "Minimum time in seconds between generated RA messages,
            should be less than 0.75* max-ra-interval."
    ::= { f3L3TrafficIPv6InterfaceEntry 17 }

f3L3TrafficIPv6IfRouterLifeTime OBJECT-TYPE
    SYNTAX      Unsigned32
    MAX-ACCESS  read-write
    STATUS      current
    DESCRIPTION
           "Time in seconds the router can be used as a default router,
            should be larger than max-ra-interval."
    ::= { f3L3TrafficIPv6InterfaceEntry 18 }

f3L3TrafficIPv6IfReachableTime OBJECT-TYPE
    SYNTAX      Unsigned32
    MAX-ACCESS  read-write
    STATUS      current
    DESCRIPTION
           "time in milliseconds, that a node assumes a neighbor is reachable after having received
            a reachability confirmation, 0 means unspecified."
    ::= { f3L3TrafficIPv6InterfaceEntry 19 }

f3L3TrafficIPv6IfRaDhcpMoreConfigEnabled OBJECT-TYPE
    SYNTAX      TruthValue
    MAX-ACCESS  read-write
    STATUS      current
    DESCRIPTION
           "RA More configurations via DHCP."
    ::= { f3L3TrafficIPv6InterfaceEntry 20 }

f3L3TrafficIPv6IfRaManagedAddressConfigEnabled OBJECT-TYPE
    SYNTAX      TruthValue
    MAX-ACCESS  read-write
    STATUS      current
    DESCRIPTION
           "RA Managed Address Config Control."
    ::= { f3L3TrafficIPv6InterfaceEntry 21 }

f3L3TrafficIPv6IfRaRDNSSOptionEnabled OBJECT-TYPE
    SYNTAX      TruthValue
    MAX-ACCESS  read-write
    STATUS      current
    DESCRIPTION
           "Control Recursive DNS server option presence in the RA messages."
    ::= { f3L3TrafficIPv6InterfaceEntry 22 }

f3L3TrafficIPv6IfRaRDNSSLifeTime OBJECT-TYPE
    SYNTAX      Unsigned32
    MAX-ACCESS  read-write
    STATUS      current
    DESCRIPTION
           "Set the Lifetime field of the RDNSS option."
    ::= { f3L3TrafficIPv6InterfaceEntry 23 }

f3L3TrafficIPv6IfRaDNSSList OBJECT-TYPE
    SYNTAX      DisplayString
    MAX-ACCESS  read-write
    STATUS      current
    DESCRIPTION
           "list of IPv6 addresses of DNS servers."
    ::= { f3L3TrafficIPv6InterfaceEntry 24 }

f3L3TrafficIPv6IfRaDefaultRouterPreference OBJECT-TYPE
    SYNTAX      NdpRaDefaultRouterPreference
    MAX-ACCESS  read-write
    STATUS      current
    DESCRIPTION
           "Specifies Default Router preference field in RA according to RFC4191."
    ::= { f3L3TrafficIPv6InterfaceEntry 25 }

f3L3TrafficIPv6IfDupAddrDetectControl OBJECT-TYPE
    SYNTAX      TruthValue
    MAX-ACCESS  read-write
    STATUS      current
    DESCRIPTION
           "Allows enabling/disabling of DAD on this interface."
    ::= { f3L3TrafficIPv6InterfaceEntry 26 }

f3L3TrafficIPv6IfDupAddrDetectTransmits OBJECT-TYPE
    SYNTAX      Unsigned32
    MAX-ACCESS  read-write
    STATUS      current
    DESCRIPTION
           "Specify number of consequent NS messages sent by this interface."
    ::= { f3L3TrafficIPv6InterfaceEntry 27 }

f3L3TrafficIPv6IfDupAddrDetectRetransTimer OBJECT-TYPE
    SYNTAX      Unsigned32
    MAX-ACCESS  read-write
    STATUS      current
    DESCRIPTION
           "Interval in ms between consecutive NS messages and  as well as the time a node
            waits after sending the last NS  before ending the DAD."
    ::= { f3L3TrafficIPv6InterfaceEntry 28 }

f3L3TrafficIPv6IfStorageType OBJECT-TYPE
    SYNTAX      StorageType
    MAX-ACCESS  read-create
    STATUS      current
    DESCRIPTION
        "The storage type for this conceptual row."
   ::= { f3L3TrafficIPv6InterfaceEntry 29 }

f3L3TrafficIPv6IfRowStatus OBJECT-TYPE
    SYNTAX      RowStatus
    MAX-ACCESS  read-create
    STATUS      current
    DESCRIPTION
        "The status of this row.  An entry MUST NOT exist in the 
        active state unless all objects in the entry have an 
        appropriate value, as described
        in the description clause for each writable object.

        The values of f3L3TrafficIPv6IfRowStatus supported are
        createAndGo(4) and destroy(6).  All mandatory attributes
        must be specified in a single SNMP SET request with
        f3L3TrafficIPv6IfRowStatus value as createAndGo(4).
        Upon successful row creation, this object has a
        value of active(1).

        The f3L3TrafficIPv6IfRowStatus object may be modified if
        the associated instance of this object is equal to active(1)."
   ::= { f3L3TrafficIPv6InterfaceEntry 30 }

f3L3TrafficIPv6IfAction OBJECT-TYPE
    SYNTAX      TrafficIpv6InterfaceActionType
    MAX-ACCESS  read-write
    STATUS      current
    DESCRIPTION
           "This objects describes action set on this traffic ip interface."
    ::= { f3L3TrafficIPv6InterfaceEntry 31 }


--
--  L3 traffic ipv6 Address Table
--

f3L3TrafficIPv6AddressTable  OBJECT-TYPE
    SYNTAX      SEQUENCE OF F3L3TrafficIPv6AddressEntry
    MAX-ACCESS  not-accessible
    STATUS      current
    DESCRIPTION
            "Traffic IPv6 interface address table."
    ::= { f3L3Objects 27 }

f3L3TrafficIPv6AddressEntry  OBJECT-TYPE
    SYNTAX      F3L3TrafficIPv6AddressEntry
    MAX-ACCESS  not-accessible
    STATUS      current
    DESCRIPTION
            "A conceptual row in the f3L3TrafficIPv6AddressTable."
    INDEX { neIndex, shelfIndex, slotIndex,
            f3L3FlowPointPortIndex, f3L3FlowPointIndex, 
            f3L3TrafficIPv6IfIndex, f3L3TrafficIPv6AddrIndex }
    ::= { f3L3TrafficIPv6AddressTable 1 }

F3L3TrafficIPv6AddressEntry ::= SEQUENCE {
    f3L3TrafficIPv6AddrIndex                               Integer32,
    f3L3TrafficIPv6AddrAssignMode                          Ipv6AddressAssignMode,
    f3L3TrafficIPv6AddrUnicastAddr                         Ipv6Address,
    f3L3TrafficIPv6AddrUnicastAddrPrefixLength             Integer32,
    f3L3TrafficIPv6AddrUnicastAddrAutoGenPrefix            DisplayString,
    f3L3TrafficIPv6AddrStorageType                         StorageType,
    f3L3TrafficIPv6AddrRowStatus                           RowStatus
}

f3L3TrafficIPv6AddrIndex OBJECT-TYPE
    SYNTAX      Integer32
    MAX-ACCESS  not-accessible
    STATUS      current
    DESCRIPTION
           "The unique integer index value corresponding to a traffic ipv6 interface unicast address."
    ::= { f3L3TrafficIPv6AddressEntry 1 }

f3L3TrafficIPv6AddrAssignMode OBJECT-TYPE
    SYNTAX      Ipv6AddressAssignMode
    MAX-ACCESS  read-write
    STATUS      current
    DESCRIPTION
           "The assignment mode of IPv6 Unicast Address."
    ::= { f3L3TrafficIPv6AddressEntry 2 }

f3L3TrafficIPv6AddrUnicastAddr OBJECT-TYPE
    SYNTAX      Ipv6Address
    MAX-ACCESS  read-write
    STATUS      current
    DESCRIPTION
           "This is IPv6 Unicast Address."
    ::= { f3L3TrafficIPv6AddressEntry 3 }

f3L3TrafficIPv6AddrUnicastAddrPrefixLength OBJECT-TYPE
    SYNTAX      Integer32
    MAX-ACCESS  read-write
    STATUS      current
    DESCRIPTION
           "This is prefix length of the unicast address."
    ::= { f3L3TrafficIPv6AddressEntry 4 }

f3L3TrafficIPv6AddrUnicastAddrAutoGenPrefix OBJECT-TYPE
    SYNTAX      DisplayString
    MAX-ACCESS  read-write
    STATUS      current
    DESCRIPTION
           "This is prefix of the unicast address in automatic address assignment mode."
    ::= { f3L3TrafficIPv6AddressEntry 5 }

f3L3TrafficIPv6AddrStorageType OBJECT-TYPE
    SYNTAX      StorageType
    MAX-ACCESS  read-create
    STATUS      current
    DESCRIPTION
        "The storage type for this conceptual row."
   ::= { f3L3TrafficIPv6AddressEntry 6 }

f3L3TrafficIPv6AddrRowStatus OBJECT-TYPE
    SYNTAX      RowStatus
    MAX-ACCESS  read-create
    STATUS      current
    DESCRIPTION
        "The status of this row.  An entry MUST NOT exist in the 
        active state unless all objects in the entry have an 
        appropriate value, as described
        in the description clause for each writable object.

        The values of f3L3TrafficIPv6AddrRowStatus supported are
        createAndGo(4) and destroy(6).  All mandatory attributes
        must be specified in a single SNMP SET request with
        f3L3TrafficIPv6AddrRowStatus value as createAndGo(4).
        Upon successful row creation, this object has a
        value of active(1).

        The f3L3TrafficIPv6AddrRowStatus object may be modified if
        the associated instance of this object is equal to active(1)."
   ::= { f3L3TrafficIPv6AddressEntry 7 }


--
-- L3 traffic ipv6 Prefix Table
--

f3L3TrafficIPv6PrefixTable OBJECT-TYPE
    SYNTAX      SEQUENCE OF F3L3TrafficIPv6PrefixEntry
    MAX-ACCESS  not-accessible
    STATUS      current
    DESCRIPTION
        "Traffic IPv6 RA prefix table."

   ::= { f3L3Objects 28 }

f3L3TrafficIPv6PrefixEntry OBJECT-TYPE
    SYNTAX      F3L3TrafficIPv6PrefixEntry
    MAX-ACCESS  not-accessible
    STATUS      current
    DESCRIPTION
        "A conceptual row in f3L3TrafficIPv6PrefixTable."
    INDEX { neIndex, shelfIndex, slotIndex,
            f3L3FlowPointPortIndex, f3L3FlowPointIndex, 
            f3L3TrafficIPv6IfIndex, f3L3TrafficIPv6PrefixIndex }

   ::= { f3L3TrafficIPv6PrefixTable 1 }

F3L3TrafficIPv6PrefixEntry ::= SEQUENCE {
    f3L3TrafficIPv6PrefixIndex                  Integer32,
    f3L3TrafficIPv6PrefixRaPrefixAdvEnabled     TruthValue,
    f3L3TrafficIPv6PrefixRaPrefix               Ipv6Address,
    f3L3TrafficIPv6PrefixRaPrefixLength         Integer32,
    f3L3TrafficIPv6PrefixValidLifeTime          Unsigned32,
    f3L3TrafficIPv6PrefixPreferredLifeTime      Unsigned32,
    f3L3TrafficIPv6PrefixStorageType            StorageType,
    f3L3TrafficIPv6PrefixRowStatus              RowStatus
}

f3L3TrafficIPv6PrefixIndex OBJECT-TYPE
    SYNTAX      Integer32
    MAX-ACCESS  not-accessible
    STATUS      current
    DESCRIPTION
           "The unique integer index value corresponding to a traffic ipv6 interface ra prefix."
    ::= { f3L3TrafficIPv6PrefixEntry 1 }

f3L3TrafficIPv6PrefixRaPrefixAdvEnabled OBJECT-TYPE
    SYNTAX      TruthValue
    MAX-ACCESS  read-write
    STATUS      current
    DESCRIPTION
           "This attribute is to enable to Advertise prefix to link in router mode."
    ::= { f3L3TrafficIPv6PrefixEntry 2 }

f3L3TrafficIPv6PrefixRaPrefix OBJECT-TYPE
    SYNTAX      Ipv6Address
    MAX-ACCESS  read-write
    STATUS      current
    DESCRIPTION
           "This is the IPv6 Prefix to be dispatched to the link in Router mode."
    ::= { f3L3TrafficIPv6PrefixEntry 3 }

f3L3TrafficIPv6PrefixRaPrefixLength OBJECT-TYPE
    SYNTAX      Integer32
    MAX-ACCESS  read-write
    STATUS      current
    DESCRIPTION
           "Prefix length."
    ::= { f3L3TrafficIPv6PrefixEntry 4 }

f3L3TrafficIPv6PrefixValidLifeTime OBJECT-TYPE
    SYNTAX      Unsigned32
    MAX-ACCESS  read-write
    STATUS      current
    DESCRIPTION
           "This attribute is used to specify fixed Valid lifetime of distributed prefix in seconds
            All ones may be set for unlimited lifetime."
    ::= { f3L3TrafficIPv6PrefixEntry 5 }

f3L3TrafficIPv6PrefixPreferredLifeTime OBJECT-TYPE
    SYNTAX      Unsigned32
    MAX-ACCESS  read-write
    STATUS      current
    DESCRIPTION
           "This attribute is used to specify fixed time interval for unrestricted use of prefix.
            When this time has been expired the address is considered as deprecated as specified
            in RFC4862 Preferred lifetime shall not be greater than the Valid Lifetime. All
            ones may be set for unlimited lifetime."
    ::= { f3L3TrafficIPv6PrefixEntry 6 }

f3L3TrafficIPv6PrefixStorageType OBJECT-TYPE
    SYNTAX      StorageType
    MAX-ACCESS  read-create
    STATUS      current
    DESCRIPTION
        "The storage type for this conceptual row."
   ::= { f3L3TrafficIPv6PrefixEntry 7 }

f3L3TrafficIPv6PrefixRowStatus OBJECT-TYPE
    SYNTAX      RowStatus
    MAX-ACCESS  read-create
    STATUS      current
    DESCRIPTION
        "The status of this row.  An entry MUST NOT exist in the 
        active state unless all objects in the entry have an 
        appropriate value, as described
        in the description clause for each writable object.

        The values of f3L3TrafficIPv6PrefixRowStatus supported are
        createAndGo(4) and destroy(6).  All mandatory attributes
        must be specified in a single SNMP SET request with
        f3L3TrafficIPv6PrefixRowStatus value as createAndGo(4).
        Upon successful row creation, this object has a
        value of active(1).

        The f3L3TrafficIPv6PrefixRowStatus object may be modified if
        the associated instance of this object is equal to active(1)."
   ::= { f3L3TrafficIPv6PrefixEntry 8 }


--
-- L3 traffic ipv6 Ndp Table
--

f3L3TrafficIPv6NdpTable OBJECT-TYPE
    SYNTAX      SEQUENCE OF F3L3TrafficIPv6NdpEntry
    MAX-ACCESS  not-accessible
    STATUS      current
    DESCRIPTION
        "Traffic IPv6 NDP table."

   ::= { f3L3Objects 29 }

f3L3TrafficIPv6NdpEntry OBJECT-TYPE
    SYNTAX      F3L3TrafficIPv6NdpEntry
    MAX-ACCESS  not-accessible
    STATUS      current
    DESCRIPTION
        "A conceptual row in f3L3TrafficIPv6NdpTable."
    INDEX { neIndex, shelfIndex, slotIndex,
            f3L3FlowPointPortIndex, f3L3FlowPointIndex, 
            f3L3TrafficIPv6IfIndex, f3L3TrafficIPv6NdpIPv6Addr }

   ::= { f3L3TrafficIPv6NdpTable 1 }

F3L3TrafficIPv6NdpEntry ::= SEQUENCE {
    f3L3TrafficIPv6NdpIPv6Addr              Ipv6Address,
    f3L3TrafficIPv6NdpInterface             DisplayString,
    f3L3TrafficIPv6NdpMacAddress            MacAddress,
    f3L3TrafficIPv6NdpType                  IpEntryType,
    f3L3TrafficIPv6NdpReachabilityState     NdpNeighborReachabilityState,
    f3L3TrafficIPv6NdpAge                   Integer32,
    f3L3TrafficIPv6NdpStorageType           StorageType,
    f3L3TrafficIPv6NdpRowStatus             RowStatus
}

f3L3TrafficIPv6NdpIPv6Addr OBJECT-TYPE
    SYNTAX      Ipv6Address
    MAX-ACCESS  not-accessible
    STATUS      current
    DESCRIPTION
        "This is the IP address of the NDP Entry."
    ::= { f3L3TrafficIPv6NdpEntry 1 }

f3L3TrafficIPv6NdpInterface OBJECT-TYPE
    SYNTAX      DisplayString (SIZE (0..15))
    MAX-ACCESS  read-create
    STATUS      current
    DESCRIPTION
        "This is the IP interface for the NDP Entry."
    ::= { f3L3TrafficIPv6NdpEntry 2 }

f3L3TrafficIPv6NdpMacAddress OBJECT-TYPE
    SYNTAX      MacAddress
    MAX-ACCESS  read-create
    STATUS      current
    DESCRIPTION
        "This is the MAC address of the NDP Entry."
    ::= { f3L3TrafficIPv6NdpEntry 3 }

f3L3TrafficIPv6NdpType OBJECT-TYPE
    SYNTAX      IpEntryType
    MAX-ACCESS  read-create
    STATUS      current
    DESCRIPTION
        "The type of NDP Entry.
         Note that static entries can be created."
    ::= { f3L3TrafficIPv6NdpEntry 4 }

f3L3TrafficIPv6NdpReachabilityState OBJECT-TYPE
    SYNTAX      NdpNeighborReachabilityState
    MAX-ACCESS  read-only
    STATUS      current
    DESCRIPTION
        "This is the reachability state of the NDP Entry."
    ::= { f3L3TrafficIPv6NdpEntry 5 }

f3L3TrafficIPv6NdpAge OBJECT-TYPE
    SYNTAX      Integer32
    MAX-ACCESS  read-only
    STATUS      current
    DESCRIPTION
        "Indicates entry age in seconds."
    ::= { f3L3TrafficIPv6NdpEntry 6 }

f3L3TrafficIPv6NdpStorageType OBJECT-TYPE
    SYNTAX      StorageType
    MAX-ACCESS  read-create
    STATUS      current
    DESCRIPTION
        "The storage type for this conceptual row."
   ::= { f3L3TrafficIPv6NdpEntry 7 }

f3L3TrafficIPv6NdpRowStatus OBJECT-TYPE
    SYNTAX      RowStatus
    MAX-ACCESS  read-create
    STATUS      current
    DESCRIPTION
        "The status of this row.  An entry MUST NOT exist in the 
        active state unless all objects in the entry have an 
        appropriate value, as described
        in the description clause for each writable object.

        The values of f3L3TrafficIPv6NdpRowStatus supported are
        createAndGo(4) and destroy(6).  All mandatory attributes
        must be specified in a single SNMP SET request with
        f3L3TrafficIPv6NdpRowStatus value as createAndGo(4).
        Upon successful row creation, this object has a
        value of active(1).

        The f3L3TrafficIPv6NdpRowStatus object may be modified if
        the associated instance of this object is equal to active(1)."
   ::= { f3L3TrafficIPv6NdpEntry 8 }

--
--  L3 taffic ipv6 route Table
--
f3L3TrafficIpv6RouteTable  OBJECT-TYPE
    SYNTAX      SEQUENCE OF F3L3TrafficIpv6RouteEntry
    MAX-ACCESS  not-accessible
    STATUS      current
    DESCRIPTION
            "A list of entries for the L3 Traffic Ipv6 route.
             Must set f3VrfActionX as optimizeIpv6RouteRetrieve(7) before get data from this table."
    ::= { f3L3Objects 30 }

f3L3TrafficIpv6RouteEntry  OBJECT-TYPE
    SYNTAX      F3L3TrafficIpv6RouteEntry
    MAX-ACCESS  not-accessible
    STATUS      current
    DESCRIPTION
            "A conceptual row in the f3L3TrafficIpv6RouteTable."
    INDEX { neIndex, f3VrfIndex, 
            f3L3TrafficIpv6RouteDest, f3L3TrafficIpv6RoutePrefixLength, 
            f3L3TrafficIpv6RouteGateway, f3L3TrafficIpv6RouteInterface }
    ::= { f3L3TrafficIpv6RouteTable 1 }

F3L3TrafficIpv6RouteEntry ::= SEQUENCE {
    f3L3TrafficIpv6RouteDest                                Ipv6Address,
    f3L3TrafficIpv6RoutePrefixLength                        Integer32,
    f3L3TrafficIpv6RouteGateway                             Ipv6Address,
    f3L3TrafficIpv6RouteInterface                           DisplayString,
    f3L3TrafficIpv6RouteMetric                              Integer32,
    f3L3TrafficIpv6RouteType                                IpEntryType,
    f3L3TrafficIpv6RouteAdvertise                           TruthValue,
    f3L3TrafficIpv6RouteStatus                              TrafficIpRouteStatus,
    f3L3TrafficIpv6RouteFlags                               RouteFlags,
    f3L3TrafficIpv6RouteOrigin                              TrafficIpRouteOriginType,
    f3L3TrafficIpv6RouteStorageType                         StorageType,
    f3L3TrafficIpv6RouteRowStatus                           RowStatus
}

f3L3TrafficIpv6RouteDest OBJECT-TYPE
    SYNTAX      Ipv6Address
    MAX-ACCESS  not-accessible
    STATUS      current
    DESCRIPTION
        "The destination IP address of this route. This object
         may not take a Multicast (Class  D) address value.
         Any assignment (implicit or otherwise) of an instance
         of  this  object to a value x must be rejected if
         the bitwise logical-AND of x with the value of the
         corresponding instance of the static-route-mask
         attribute is not equal to x."
   ::= { f3L3TrafficIpv6RouteEntry 1 }

f3L3TrafficIpv6RoutePrefixLength OBJECT-TYPE
    SYNTAX      Integer32
    MAX-ACCESS  not-accessible
    STATUS      current
    DESCRIPTION
        "Indicate the mask to be logically ANDed with the
         destination  address before being compared to
         the value in the cmStaticRouteDest field. For
         those systems that do not support arbitrary
         subnet masks, an agent constructs the value  of
         the static route mask by reference to the
         IP Address Class. Any assignment (implicit or
         otherwise) of an instance of this object to a
         value x must be rejected if the bitwise logical AND
         of x with the value of the corresponding instance
         of the static-route-dest attribute is not
         equal to static route destination."
   ::= { f3L3TrafficIpv6RouteEntry 2 }

f3L3TrafficIpv6RouteGateway OBJECT-TYPE
    SYNTAX      Ipv6Address
    MAX-ACCESS  not-accessible
    STATUS      current
    DESCRIPTION
        "The address of the next router en route."
   ::= { f3L3TrafficIpv6RouteEntry 3 }

f3L3TrafficIpv6RouteInterface OBJECT-TYPE
    SYNTAX      DisplayString (SIZE (0..15))
    MAX-ACCESS  not-accessible
    STATUS      current
    DESCRIPTION
        "Name of the IP interface for the interface
         static route."
   ::= { f3L3TrafficIpv6RouteEntry 4 }

f3L3TrafficIpv6RouteMetric OBJECT-TYPE
    SYNTAX      Integer32
    MAX-ACCESS  read-write
    STATUS      current
    DESCRIPTION
        "The primary routing  metric for this route.
         The semantics of this metric are determined by
         the routing-protocol specified in the route's
         cmStaticRouteProto value. If  this metric is not
         used, its value should be set to 1."
   ::= { f3L3TrafficIpv6RouteEntry 5 }

f3L3TrafficIpv6RouteType OBJECT-TYPE
    SYNTAX      IpEntryType
    MAX-ACCESS  read-create
    STATUS      current
    DESCRIPTION
        "Indicates it is dynamic or static route."
   ::= { f3L3TrafficIpv6RouteEntry 6 }

f3L3TrafficIpv6RouteAdvertise OBJECT-TYPE
    SYNTAX      TruthValue
    MAX-ACCESS  read-create
    STATUS      current
    DESCRIPTION
        "Indicates whether this static route will be
         advertised via routing protocol."
   ::= { f3L3TrafficIpv6RouteEntry 7 }

f3L3TrafficIpv6RouteStatus OBJECT-TYPE
    SYNTAX      TrafficIpRouteStatus
    MAX-ACCESS  read-only
    STATUS      current
    DESCRIPTION
        "It specifies the traffic Ipv6 route status."
   ::= { f3L3TrafficIpv6RouteEntry 8 }

f3L3TrafficIpv6RouteFlags OBJECT-TYPE
    SYNTAX      RouteFlags
    MAX-ACCESS  read-only
    STATUS      current
    DESCRIPTION
        "It specifies the traffic Ipv6 route flags."
   ::= { f3L3TrafficIpv6RouteEntry 9 }

f3L3TrafficIpv6RouteOrigin OBJECT-TYPE
    SYNTAX      TrafficIpRouteOriginType
    MAX-ACCESS  read-only
    STATUS      current
    DESCRIPTION
        "The origin of IP Route."
   ::= { f3L3TrafficIpv6RouteEntry 10 }

f3L3TrafficIpv6RouteStorageType OBJECT-TYPE
    SYNTAX      StorageType
    MAX-ACCESS  read-create
    STATUS      current
    DESCRIPTION
        "The storage type for this conceptual row."
   ::= { f3L3TrafficIpv6RouteEntry 11 }

f3L3TrafficIpv6RouteRowStatus OBJECT-TYPE
    SYNTAX      RowStatus
    MAX-ACCESS  read-create
    STATUS      current
    DESCRIPTION
        "The status of this row.  An entry MUST NOT exist in the 
        active state unless all objects in the entry have an 
        appropriate value, as described
        in the description clause for each writable object.

        The values of f3L3TrafficIpv6RouteRowStatus supported are
        createAndGo(4) and destroy(6).  All mandatory attributes
        must be specified in a single SNMP SET request with
        f3L3TrafficIpv6RouteRowStatus value as createAndGo(4).
        Upon successful row creation, this object has a
        value of active(1).

        The f3L3TrafficIpv6RouteRowStatus object may be modified if
        the associated instance of this object is equal to active(1)."
   ::= { f3L3TrafficIpv6RouteEntry 12 }


--
--  DHCP V6 Relay Agent Table
--
f3DhcpV6RelayAgentTable  OBJECT-TYPE
    SYNTAX      SEQUENCE OF F3DhcpV6RelayAgentEntry
    MAX-ACCESS  not-accessible
    STATUS      current
    DESCRIPTION
            "A list of entries for the Dhcp V6 Relay Agent."
    ::= { f3L3Objects 31 }

f3DhcpV6RelayAgentEntry  OBJECT-TYPE
    SYNTAX      F3DhcpV6RelayAgentEntry
    MAX-ACCESS  not-accessible
    STATUS      current
    DESCRIPTION
            "A conceptual row in the f3DhcpV6RelayAgentTable."
    INDEX { neIndex, f3DhcpV6RelayAgentIndex }
    ::= { f3DhcpV6RelayAgentTable 1 }

F3DhcpV6RelayAgentEntry ::= SEQUENCE {
    f3DhcpV6RelayAgentIndex                               Integer32,
    f3DhcpV6RelayAgentAlias                               F3DisplayString,
    f3DhcpV6RelayAgentAdminState                          AdminState,
    f3DhcpV6RelayAgentSecondaryState                      SecondaryState,
    f3DhcpV6RelayAgentOperationalState                    OperationalState,
    f3DhcpV6RelayAgentServerIpAddress                     Ipv6Address,
    f3DhcpV6RelayAgentServerIpInteface                    VariablePointer,
    f3DhcpV6RelayAgentStorageType                         StorageType,
    f3DhcpV6RelayAgentRowStatus                           RowStatus,
    f3DhcpV6RelayAgentServerIpAddressList                 DisplayString
}

f3DhcpV6RelayAgentIndex OBJECT-TYPE
    SYNTAX      Integer32
    MAX-ACCESS  not-accessible
    STATUS      current
    DESCRIPTION
        "The integer index value describes the dhcp-relay-agent index."
   ::= { f3DhcpV6RelayAgentEntry 1 }

f3DhcpV6RelayAgentAlias OBJECT-TYPE
    SYNTAX      F3DisplayString (SIZE (0..256))
    MAX-ACCESS  read-write
    STATUS      current
    DESCRIPTION
        "The DHCP relay agent alias."
   ::= { f3DhcpV6RelayAgentEntry 2 }

f3DhcpV6RelayAgentAdminState OBJECT-TYPE
    SYNTAX      AdminState
    MAX-ACCESS  read-write
    STATUS      current
    DESCRIPTION
           "This object represents the Administrative State of the agent."
    ::= { f3DhcpV6RelayAgentEntry 3 }

f3DhcpV6RelayAgentSecondaryState OBJECT-TYPE
    SYNTAX      SecondaryState
    MAX-ACCESS  read-only
    STATUS      current
    DESCRIPTION
           "This object represents the Secondary State of the agent."
    ::= { f3DhcpV6RelayAgentEntry 4 }

f3DhcpV6RelayAgentOperationalState OBJECT-TYPE
    SYNTAX      OperationalState
    MAX-ACCESS  read-only
    STATUS      current
    DESCRIPTION
           "This object represents the Operational State of the agent."
    ::= { f3DhcpV6RelayAgentEntry 5 }

f3DhcpV6RelayAgentServerIpAddress OBJECT-TYPE
    SYNTAX      Ipv6Address
    MAX-ACCESS  read-write
    STATUS      current
    DESCRIPTION
        "The Ipv6 address of this DCHP relay agent."
   ::= { f3DhcpV6RelayAgentEntry 6 }

f3DhcpV6RelayAgentServerIpInteface OBJECT-TYPE
    SYNTAX      VariablePointer
    MAX-ACCESS  read-write
    STATUS      current
    DESCRIPTION
         "This object describes the server Ip Interface."
    ::= { f3DhcpV6RelayAgentEntry 7 }

f3DhcpV6RelayAgentStorageType OBJECT-TYPE
    SYNTAX      StorageType
    MAX-ACCESS  read-create
    STATUS      current
    DESCRIPTION
        "The storage type for this conceptual row."
   ::= { f3DhcpV6RelayAgentEntry 8 }

f3DhcpV6RelayAgentRowStatus OBJECT-TYPE
    SYNTAX      RowStatus
    MAX-ACCESS  read-create
    STATUS      current
    DESCRIPTION
        "The status of this row.  An entry MUST NOT exist in the 
        active state unless all objects in the entry have an 
        appropriate value, as described
        in the description clause for each writable object.

        The values of f3DhcpV6RelayAgentRowStatus supported are
        createAndGo(4) and destroy(6).  All mandatory attributes
        must be specified in a single SNMP SET request with
        f3DhcpV6RelayAgentRowStatus value as createAndGo(4).
        Upon successful row creation, this object has a
        value of active(1).

        The f3DhcpV6RelayAgentRowStatus object may be modified if
        the associated instance of this object is equal to active(1)."
   ::= { f3DhcpV6RelayAgentEntry 9 }

f3DhcpV6RelayAgentServerIpAddressList OBJECT-TYPE
    SYNTAX      DisplayString
    MAX-ACCESS  read-create
    STATUS      current
    DESCRIPTION
           "DHCP Server IPv6 Address List(ie. 10::10,10::20)."
    ::= { f3DhcpV6RelayAgentEntry 10 }
    
--
--
--
f3DhcpV6RelayAgentClientTrafficIpIfMemberTable  OBJECT-TYPE
    SYNTAX      SEQUENCE OF F3DhcpV6RelayAgentClientTrafficIpIfMemberEntry
    MAX-ACCESS  not-accessible
    STATUS      current
    DESCRIPTION
            "A list of entries for the Dhcp V6 Relay Agent Client Traffic Ip Interface member."
    ::= { f3L3Objects 32 }

f3DhcpV6RelayAgentClientTrafficIpIfMemberEntry  OBJECT-TYPE
    SYNTAX      F3DhcpV6RelayAgentClientTrafficIpIfMemberEntry
    MAX-ACCESS  not-accessible
    STATUS      current
    DESCRIPTION
            "A conceptual row in the f3DhcpV6RelayAgentClientTrafficIpIfMemberTable."
    INDEX { neIndex, f3DhcpV6RelayAgentIndex, f3DhcpV6RelayAgentClientTrafficIpIfMemberObject }
    ::= { f3DhcpV6RelayAgentClientTrafficIpIfMemberTable 1 }

F3DhcpV6RelayAgentClientTrafficIpIfMemberEntry ::= SEQUENCE {
    f3DhcpV6RelayAgentClientTrafficIpIfMemberObject             VariablePointer,
    f3DhcpV6RelayAgentClientTrafficIpIfMemberStorageType        StorageType,
    f3DhcpV6RelayAgentClientTrafficIpIfMemberRowStatus          RowStatus
}

f3DhcpV6RelayAgentClientTrafficIpIfMemberObject OBJECT-TYPE
    SYNTAX      VariablePointer
    MAX-ACCESS  not-accessible
    STATUS      current
    DESCRIPTION
           "This object describes the Client traffic ip interface."
    ::= { f3DhcpV6RelayAgentClientTrafficIpIfMemberEntry 1 }

f3DhcpV6RelayAgentClientTrafficIpIfMemberStorageType OBJECT-TYPE
    SYNTAX      StorageType
    MAX-ACCESS  read-create
    STATUS      current
    DESCRIPTION
           "The type of storage configured for this entry."
    ::= { f3DhcpV6RelayAgentClientTrafficIpIfMemberEntry 2 }

f3DhcpV6RelayAgentClientTrafficIpIfMemberRowStatus OBJECT-TYPE
    SYNTAX      RowStatus
    MAX-ACCESS  read-create
    STATUS      current
    DESCRIPTION
           "The status of this row.
          	An entry MUST NOT exist in the active state unless all
          	objects in the entry have an appropriate value, as described
          	in the description clause for each writable object.
 	
          	The values of f3DhcpV6RelayAgentClientTrafficIpIfMemberRowStatus supported are
          	createAndGo(4) and destroy(6).  All mandatory attributes
          	must be specified in a single SNMP SET request with
          	f3DhcpV6RelayAgentClientTrafficIpIfMemberRowStatus value as createAndGo(4).
          	Upon successful row creation, this object has a
          	value of active(1).
 	
          	The f3DhcpV6RelayAgentClientTrafficIpIfMemberRowStatus object may be modified if
          	the associated instance of this object is equal to active(1)."
    ::= { f3DhcpV6RelayAgentClientTrafficIpIfMemberEntry 3 }

--
-- cm L3 FlowPoint table. supported in XGPRO NIDs
--
cmL3FlowPointTable  OBJECT-TYPE
    SYNTAX      SEQUENCE OF CML3FlowPointEntry
    MAX-ACCESS  not-accessible
    STATUS      current
    DESCRIPTION
            "A list of entries for the L3 flowpoint."
    ::= { f3L3Objects 33 }

cmL3FlowPointEntry  OBJECT-TYPE
    SYNTAX      CML3FlowPointEntry
    MAX-ACCESS  not-accessible
    STATUS      current
    DESCRIPTION
            "A conceptual row in the cmL3FlowPointTable."
    INDEX { neIndex, shelfIndex, slotIndex, cmL3FlowPointPortIndex, cmL3FlowPointIndex }
    ::= { cmL3FlowPointTable 1 }


CML3FlowPointEntry ::= SEQUENCE {
    cmL3FlowPointPortIndex                           Integer32,
    cmL3FlowPointIndex                               Integer32,
    cmL3FlowPointAlias                               F3DisplayString,
    cmL3FlowPointAdminState                          AdminState,
    cmL3FlowPointSecondaryState                      SecondaryState,
    cmL3FlowPointOperationalState                    OperationalState,
    cmL3FlowPointMultiCOSEnabled                     TruthValue,
    cmL3FlowPointCOS                                 Integer32,
    cmL3FlowPointUntaggedMemberShipEnabled           TruthValue,
    cmL3FlowPointOuterTagMemberShipEnabled           TruthValue,
    cmL3FlowPointOuterTagMemberShipVlanId            VlanId,
    cmL3FlowPointInnerTagMemberShipEnabled           TruthValue,
    cmL3FlowPointInnerTagMemberShipVlanId            VlanId,
    cmL3FlowPointFragmentedPktsFwdEnabled            TruthValue,
    cmL3FlowPointHCosMgmtEnabled                     TruthValue,
    cmL3FlowPointHCosGuaranteedBwHi                  Unsigned32,
    cmL3FlowPointHCosGuaranteedBwLo                  Unsigned32,
    cmL3FlowPointHCosMaximumBwHi                     Unsigned32,
    cmL3FlowPointHCosMaximumBwLo                     Unsigned32,
    cmL3FlowPointDscpOverwriteControl                TruthValue,
    cmL3FlowPointPriMapProfile                       VariablePointer,
    cmL3FlowPointStorageType                         StorageType,
    cmL3FlowPointRowStatus                           RowStatus,
    cmL3FlowPointAclNoMatchDisposition               AclNoMatchDispositionType,
    cmL3FlowPointWfqSegmentationCOS                  Integer32,
    cmL3FlowPointWfqGroupCOS                         Integer32,
    cmL3FlowPointWfqGroupEirLo                       Unsigned32,
    cmL3FlowPointWfqGroupEirHi                       Unsigned32,
    cmL3FlowPointEgressShapingType                   ShapingType
}

cmL3FlowPointPortIndex OBJECT-TYPE
    SYNTAX      Integer32
    MAX-ACCESS  not-accessible
    STATUS      current
    DESCRIPTION
           "The port number value."
    ::= { cmL3FlowPointEntry 1 }

cmL3FlowPointIndex OBJECT-TYPE
    SYNTAX      Integer32
    MAX-ACCESS  not-accessible
    STATUS      current
    DESCRIPTION
           "The L3 flow point number."
    ::= { cmL3FlowPointEntry 2 }

cmL3FlowPointAlias OBJECT-TYPE
    SYNTAX      F3DisplayString (SIZE (0..256))
    MAX-ACCESS  read-write
    STATUS      current
    DESCRIPTION
           "This object describes the L3 flow point alias."
    ::= { cmL3FlowPointEntry 3 }

cmL3FlowPointAdminState OBJECT-TYPE
    SYNTAX      AdminState
    MAX-ACCESS  read-write
    STATUS      current
    DESCRIPTION
           "This object describes the L3 flow point admin state."
    ::= { cmL3FlowPointEntry 4 }

cmL3FlowPointSecondaryState OBJECT-TYPE
    SYNTAX      SecondaryState
    MAX-ACCESS  read-only
    STATUS      current
    DESCRIPTION
           "This object describes the L3 flow point secondary state."
    ::= { cmL3FlowPointEntry 5 }

cmL3FlowPointOperationalState OBJECT-TYPE
    SYNTAX      OperationalState
    MAX-ACCESS  read-only
    STATUS      current
    DESCRIPTION
           "This object describes the L3 flow point operational state."
    ::= { cmL3FlowPointEntry 6 }

cmL3FlowPointMultiCOSEnabled OBJECT-TYPE
    SYNTAX      TruthValue
    MAX-ACCESS  read-write
    STATUS      current
    DESCRIPTION
           "Control to enable or disable per-COS BWPs on a FlowPoint.
            ENABLED:per-COS BWPs (CIR, EIR, CBS, EBS, CM, CF) are applied as a policing 
                     function for all ingress frames of this flowpoint.
            DISABLED:per-Flow BWP (CIR, EIR, CBS, EBS, CM, CF) is applied as a policing 
                     function for all ingress frames of this flowpoint.
            User must independently enable each COS BWP when ENABLED."
    ::= { cmL3FlowPointEntry 7 }

cmL3FlowPointCOS OBJECT-TYPE
    SYNTAX      Integer32
    MAX-ACCESS  read-write
    STATUS      current
    DESCRIPTION
           "Identifies the internal COS applied to all ingress frames of the flowpoint."
    ::= { cmL3FlowPointEntry 8 }

cmL3FlowPointUntaggedMemberShipEnabled OBJECT-TYPE
    SYNTAX      TruthValue
    MAX-ACCESS  read-write
    STATUS      current
    DESCRIPTION
           "This attribute controls untagged frames membership for the Flowpoint.
            ENABLED: Ingress untagged frame matches Flowpoint membership.
            DISABLED: Ingress untagged frame does not match Flowpoint membership."
    ::= { cmL3FlowPointEntry 9 }

cmL3FlowPointOuterTagMemberShipEnabled OBJECT-TYPE
    SYNTAX      TruthValue
    MAX-ACCESS  read-write
    STATUS      current
    DESCRIPTION
           "This attribute controls outer tag membership for the Flowpoint whether enabled."
    ::= { cmL3FlowPointEntry 10 }

cmL3FlowPointOuterTagMemberShipVlanId OBJECT-TYPE
    SYNTAX      VlanId
    MAX-ACCESS  read-write
    STATUS      current
    DESCRIPTION
           "This attribute controls outer tag VlanId membership for the Flowpoint."
    ::= { cmL3FlowPointEntry 11 }

cmL3FlowPointInnerTagMemberShipEnabled OBJECT-TYPE
    SYNTAX      TruthValue
    MAX-ACCESS  read-write
    STATUS      current
    DESCRIPTION
           "This attribute controls inner tag membership for the Flowpoint whether enabled."
    ::= { cmL3FlowPointEntry 12 }

cmL3FlowPointInnerTagMemberShipVlanId OBJECT-TYPE
    SYNTAX      VlanId
    MAX-ACCESS  read-write
    STATUS      current
    DESCRIPTION
           "This attribute controls inner tag VlanId membership for the Flowpoint."
    ::= { cmL3FlowPointEntry 13 }

cmL3FlowPointFragmentedPktsFwdEnabled OBJECT-TYPE
    SYNTAX      TruthValue
    MAX-ACCESS  read-write
    STATUS      current
    DESCRIPTION
           "This attribute specifies whether received IP Packets with More Fragments
            flag should be forwarded by the FlowPoint."
    ::= { cmL3FlowPointEntry 14 }

cmL3FlowPointHCosMgmtEnabled OBJECT-TYPE
    SYNTAX      TruthValue
    MAX-ACCESS  read-write
    STATUS      current
    DESCRIPTION
           "This attribute specifies whether the Hierarchical COS shaping enabled for this flow point."
    ::= { cmL3FlowPointEntry 15 }

cmL3FlowPointHCosGuaranteedBwHi OBJECT-TYPE
    SYNTAX      Unsigned32
    MAX-ACCESS  read-write
    STATUS      current
    DESCRIPTION
           "This attribute specifies the Hierarchical COS guarranteed bandwidth 
           high 32 bits for this flow point."
    ::= { cmL3FlowPointEntry 16 }

cmL3FlowPointHCosGuaranteedBwLo OBJECT-TYPE
    SYNTAX      Unsigned32
    MAX-ACCESS  read-write
    STATUS      current
    DESCRIPTION
           "This attribute specifies the Hierarchical COS guarranteed bandwidth 
           low 32 bits for this flow point."
    ::= { cmL3FlowPointEntry 17 }

cmL3FlowPointHCosMaximumBwHi OBJECT-TYPE
    SYNTAX      Unsigned32
    MAX-ACCESS  read-write
    STATUS      current
    DESCRIPTION
           "This attribute specifies the Hierarchical COS maximum bandwidth 
           high 32 bits for this flow point."
    ::= { cmL3FlowPointEntry 18 }

cmL3FlowPointHCosMaximumBwLo OBJECT-TYPE
    SYNTAX      Unsigned32
    MAX-ACCESS  read-write
    STATUS      current
    DESCRIPTION
           "This attribute specifies the Hierarchical COS maximum bandwidth 
           low 32 bits for this flow point."
    ::= { cmL3FlowPointEntry 19 }

cmL3FlowPointDscpOverwriteControl OBJECT-TYPE
    SYNTAX      TruthValue
    MAX-ACCESS  read-write
    STATUS      current
    DESCRIPTION
           "This attribute allows enable dscp value overwrite."
    ::= { cmL3FlowPointEntry 20 }

cmL3FlowPointPriMapProfile OBJECT-TYPE
    SYNTAX      VariablePointer
    MAX-ACCESS  read-write
    STATUS      current
    DESCRIPTION
           "This attribute allows specify the priority map profile."
    ::= { cmL3FlowPointEntry 21 }


cmL3FlowPointStorageType OBJECT-TYPE
    SYNTAX     StorageType
    MAX-ACCESS read-create
    STATUS     current
    DESCRIPTION
            "The type of storage configured for this entry."
    ::= { cmL3FlowPointEntry 22 }

cmL3FlowPointRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmL3FlowPointRowStatus supported are
            createAndGo(4) and destroy(6).  All mandatory attributes
            must be specified in a single SNMP SET request with
            cmL3FlowPointRowStatus value as createAndGo(4).
            Upon successful row creation, this variable has a
            value of active(1).

            The cmL3FlowPointRowStatus object may be modified if
            the associated instance of this object is equal to active(1)."
    ::= { cmL3FlowPointEntry 23 }

cmL3FlowPointAclNoMatchDisposition OBJECT-TYPE
    SYNTAX      AclNoMatchDispositionType
    MAX-ACCESS  read-write
    STATUS      current
    DESCRIPTION
            "This attribute allows specify ACL no match disposition type"
    ::= { cmL3FlowPointEntry 24 }

cmL3FlowPointWfqSegmentationCOS OBJECT-TYPE
    SYNTAX      Integer32
    MAX-ACCESS  read-write
    STATUS      current
    DESCRIPTION
           "This object is used to specify wfq segmentation COS value."
    ::= { cmL3FlowPointEntry 25 }

cmL3FlowPointWfqGroupCOS OBJECT-TYPE
    SYNTAX      Integer32
    MAX-ACCESS  read-write
    STATUS      current
    DESCRIPTION
           "This object is used to specify wfq group COS value."
    ::= { cmL3FlowPointEntry 26 }

cmL3FlowPointWfqGroupEirLo OBJECT-TYPE
    SYNTAX      Unsigned32
    MAX-ACCESS  read-write
    STATUS      current
    DESCRIPTION
           "This object is used to specify wfq group EIR low 32 bits value."
    ::= { cmL3FlowPointEntry 27 }

cmL3FlowPointWfqGroupEirHi OBJECT-TYPE
    SYNTAX      Unsigned32
    MAX-ACCESS  read-write
    STATUS      current
    DESCRIPTION
           "This object is used to specify wfq group EIR high 32 bits value."
    ::= { cmL3FlowPointEntry 28 }
    
cmL3FlowPointEgressShapingType OBJECT-TYPE
    SYNTAX     ShapingType
    MAX-ACCESS read-write
    STATUS     current
    DESCRIPTION
       "This object allows specification of Shaping Type for Flow Point"
    ::= { cmL3FlowPointEntry 29 }



--
-- L3 Policer - used by Xgpro product line
--
cmL3QosPolicerTable  OBJECT-TYPE
    SYNTAX      SEQUENCE OF CML3QosPolicerEntry
    MAX-ACCESS  not-accessible
    STATUS      current
    DESCRIPTION
        "A list of entries corresponding to Ethernet Quality of Service 
         Policer for configuration purposes."
    ::= { f3L3Objects 34 }

cmL3QosPolicerEntry OBJECT-TYPE
    SYNTAX      CML3QosPolicerEntry 
    MAX-ACCESS  not-accessible
    STATUS      current
    DESCRIPTION
         "A conceptual row in the cmL3QosPolicerTable. 
          These entries represent a Quality of Service Policer."
    INDEX { neIndex, shelfIndex, slotIndex, 
            cmL3FlowPointPortIndex, cmL3FlowPointIndex, cmL3QosPolicerIndex }
    ::= { cmL3QosPolicerTable 1 }

CML3QosPolicerEntry ::= SEQUENCE {
    cmL3QosPolicerIndex                 Integer32,
    cmL3QosPolicerAdminState            AdminState,
    cmL3QosPolicerOperationalState      OperationalState,
    cmL3QosPolicerSecondaryState        SecondaryState,
    cmL3QosPolicerCIRLo                 Unsigned32,
    cmL3QosPolicerCIRHi                 Unsigned32,
    cmL3QosPolicerEIRLo                 Unsigned32,
    cmL3QosPolicerEIRHi                 Unsigned32,
    cmL3QosPolicerCBS                   Integer32,
    cmL3QosPolicerEBS                   Integer32,
    cmL3QosPolicerAlgorithm             PolicerAlgorithmType,
    cmL3QosPolicerColorMode             PolicerColorMode,
    cmL3QosPolicerCouplingFlag          TruthValue,
    cmL3QosPolicerCIRMaxHi              Unsigned32,
    cmL3QosPolicerCIRMaxLo              Unsigned32,
    cmL3QosPolicerEIRMaxHi              Unsigned32,
    cmL3QosPolicerEIRMaxLo              Unsigned32,
    cmL3QosPolicerEnvelopeObject        VariablePointer,
    cmL3QosPolicerRank                  Integer32,
    cmL3QosPolicerPolicingEnabled       TruthValue,
    cmL3QosPolicerStorageType           StorageType,
    cmL3QosPolicerRowStatus             RowStatus
}

cmL3QosPolicerIndex OBJECT-TYPE
    SYNTAX      Integer32 (1..16)
    MAX-ACCESS  read-create
    STATUS      current
    DESCRIPTION
            "The Policer Index that represents the COS level.  This
             is applicable in case of a Multi COS flow. Index 1
             represents COS 0; Index 2 represents COS 1 and so on. 

             In release 5.6CC the range is extended to 1..16 to support duplicate
             N2A policers on a Flow. The duplicate policers are created under a Flow 
             if network interface of the Flow is ERP Group or Split Horizon Group. 
             In case of multi-cos Flow indices 1..8 represent policers of COS 0..7 
             going from Network 1 port; indices 9..16 represent policers for COS 0..7 
             going from Network 2 port.
             In case of single-cos Flow index 1 represents policer going from Network 1
             port; index 9 represents policer going from Network 2 port.
             "
    ::= { cmL3QosPolicerEntry 1 }

-- State Management params
cmL3QosPolicerAdminState OBJECT-TYPE
    SYNTAX      AdminState 
    MAX-ACCESS  read-write
    STATUS      current
    DESCRIPTION
            "This object represents the Administrative State of 
             the QOS Flow Policer." 
    ::= { cmL3QosPolicerEntry 2 }

cmL3QosPolicerOperationalState OBJECT-TYPE
    SYNTAX      OperationalState 
    MAX-ACCESS  read-only
    STATUS      current
    DESCRIPTION
            "This object represents the Operational State of the QOS Flow Policer." 
    ::= { cmL3QosPolicerEntry 3 }

cmL3QosPolicerSecondaryState OBJECT-TYPE
    SYNTAX      SecondaryState 
    MAX-ACCESS  read-only
    STATUS      current
    DESCRIPTION
            "This object represents the Secondary State of the QOS Flow Policer." 
    ::= { cmL3QosPolicerEntry 4 }

cmL3QosPolicerCIRLo OBJECT-TYPE
    SYNTAX     Unsigned32
    MAX-ACCESS read-create
    STATUS     current
    DESCRIPTION
         "This object allows specification of the Commited Information
          Rate(CIR) on Policer.  This represents the lower 32 bits of the
          CIR."
     ::= { cmL3QosPolicerEntry 5 }

cmL3QosPolicerCIRHi OBJECT-TYPE
    SYNTAX     Unsigned32
    MAX-ACCESS read-create
    STATUS     current
    DESCRIPTION
         "This object allows specification of the Commited Information
          Rate(CIR) on Policer.  This represents the upper 32 bits of the
          CIR."
     ::= { cmL3QosPolicerEntry 6 }

cmL3QosPolicerEIRLo OBJECT-TYPE
    SYNTAX     Unsigned32
    MAX-ACCESS read-create
    STATUS     current
    DESCRIPTION
         "This object allows specification of the Excess Information
          Rate(EIR) on the Policer.  This represents the lower 32 bits
          of the EIR."
     ::= { cmL3QosPolicerEntry 7 }

cmL3QosPolicerEIRHi OBJECT-TYPE
    SYNTAX     Unsigned32
    MAX-ACCESS read-create
    STATUS     current
    DESCRIPTION
         "This object allows specification of the Excess Information
          Rate(EIR) on the Policer.  This represents the upper 32 bits
          of the EIR."
     ::= { cmL3QosPolicerEntry 8 }

cmL3QosPolicerCBS OBJECT-TYPE
    SYNTAX     Integer32
    MAX-ACCESS read-create
    STATUS     current
    DESCRIPTION
         "This object allows specification of the Commited Burst Size
          (CBS) on Policer."
     ::= { cmL3QosPolicerEntry 9 }

cmL3QosPolicerEBS OBJECT-TYPE
    SYNTAX     Integer32
    MAX-ACCESS read-create
    STATUS     current
    DESCRIPTION
         "This object allows specification of the Excess Burst Size
          (EBS) on the Policer."
     ::= { cmL3QosPolicerEntry 10 }

cmL3QosPolicerAlgorithm OBJECT-TYPE
    SYNTAX      PolicerAlgorithmType 
    MAX-ACCESS  read-only
    STATUS      current
    DESCRIPTION
          "This object allows specification of Policer algorithm as
           'srTCM' (Single Rate Triple Color Marking) or 'trTCM' (Two Rate
           Triple Color Marking)."
    ::= { cmL3QosPolicerEntry 11 }

cmL3QosPolicerColorMode OBJECT-TYPE
    SYNTAX      PolicerColorMode 
    MAX-ACCESS  read-create
    STATUS      current
    DESCRIPTION
          "This object allows specification of Policer Color Mode as
           'color-aware' or 'color-blind'."
    ::= { cmL3QosPolicerEntry 12 }

cmL3QosPolicerCouplingFlag OBJECT-TYPE
    SYNTAX      TruthValue
    MAX-ACCESS  read-create
    STATUS      current
    DESCRIPTION
       "This object allows specification of Policer Coupling Flag.
        When coupling is enabled, tokens that would normally be 
        added to the C-bucket are passed to the E-bucket only once the CIR
        bucket has reached its CBS level. Therefore under this condition
        the E-bucket is being filled at the rate of CIR + EIR. 
        Normally the long term average of frames declared yellow is 
        bounded by the EIR. Coupling is a function to allow the 
        long term average of frames declared yellow to be bounded by 
        CIR + EIR. This allows a higher volume of yellow frames 
        to be delivered/received if the arrival of green marked frames 
        is low.  Tokens from the E-bucket do NOT get passed to the 
        C-bucket once the EBS level has been reached.
        Enabling coupling in combination with a provisioned EIR of 0 
        allows for a single rate three color marking (srTCM) algorithm 
        to be established.  In this situation the E-bucket is filled at the 
        CIR rate in the case the C-bucket is filled to its CBS level."
    ::= { cmL3QosPolicerEntry 13 }

cmL3QosPolicerCIRMaxHi OBJECT-TYPE
    SYNTAX     Unsigned32
    MAX-ACCESS read-write
    STATUS     current
    DESCRIPTION
         "This object allows specification of the Commited Information
          Rate(CIR) MAX on Policer.  This represents the high 32 bits."
     ::= { cmL3QosPolicerEntry 14 }

cmL3QosPolicerCIRMaxLo OBJECT-TYPE
    SYNTAX     Unsigned32
    MAX-ACCESS read-write
    STATUS     current
    DESCRIPTION
         "This object allows specification of the Commited Information
          Rate(CIR) MAX on Policer.  This represents the lower 32 bits."
     ::= { cmL3QosPolicerEntry 15 }

cmL3QosPolicerEIRMaxHi OBJECT-TYPE
    SYNTAX     Unsigned32
    MAX-ACCESS read-write
    STATUS     current
    DESCRIPTION
         "This object allows specification of the Excess Information
          Rate(EIR) MAX on the Policer.  This represents the high 32 bits."
     ::= { cmL3QosPolicerEntry 16 }

cmL3QosPolicerEIRMaxLo OBJECT-TYPE
    SYNTAX     Unsigned32
    MAX-ACCESS read-write
    STATUS     current
    DESCRIPTION
         "This object allows specification of the Excess Information
          Rate(EIR) MAX on the Policer.  This represents the lower 32 bits."
     ::= { cmL3QosPolicerEntry 17 }

cmL3QosPolicerEnvelopeObject OBJECT-TYPE
    SYNTAX     VariablePointer
    MAX-ACCESS read-write
    STATUS     current
    DESCRIPTION
         "This object allows specification of envelope object."
     ::= { cmL3QosPolicerEntry 18 }

cmL3QosPolicerRank OBJECT-TYPE
    SYNTAX     Integer32
    MAX-ACCESS read-write
    STATUS     current
    DESCRIPTION
         "This object allows specification of rank value."
     ::= { cmL3QosPolicerEntry 19 }

cmL3QosPolicerPolicingEnabled OBJECT-TYPE
    SYNTAX      TruthValue
    MAX-ACCESS  read-write
    STATUS      current
    DESCRIPTION
           "This attribute allows enable or disable policers."
    ::= { cmL3QosPolicerEntry 20 }

cmL3QosPolicerStorageType OBJECT-TYPE
    SYNTAX     StorageType
    MAX-ACCESS read-create
    STATUS     current
    DESCRIPTION
            "The type of storage configured for this entry."
    ::= { cmL3QosPolicerEntry 21 }

cmL3QosPolicerRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmL3QosPolicerRowStatus supported are
            createAndGo(4) and destroy(6).  All mandatory attributes
            must be specified in a single SNMP SET request with
            cmL3QosPolicerRowStatus value as createAndGo(4).
            Upon successful row creation, this object has a
            value of active(1).

            The cmL3QosPolicerRowStatus object may be modified if
            the associated instance of this object is equal to active(1)."
    ::= { cmL3QosPolicerEntry 22 }


--
--  L3 Port Quality of Service Shaper 
--
cmL3QosShaperTable  OBJECT-TYPE
    SYNTAX      SEQUENCE OF CML3QosShaperEntry
    MAX-ACCESS  not-accessible
    STATUS      current
    DESCRIPTION
            "A list of entries corresponding to Ethernet Access Port 
             Quality of Service Shaper for configuration purposes.
             These shapers can be managed when the Access Port is
             in evpl mode and are relevant for traffic in the
             network to access direction."
    ::= { f3L3Objects 35 }

cmL3QosShaperEntry OBJECT-TYPE
    SYNTAX      CML3QosShaperEntry 
    MAX-ACCESS  not-accessible
    STATUS      current
    DESCRIPTION
            "A conceptual row in the cmL3QosShaperTable. 
             These entries represent a Quality of Service Shaper."
    INDEX { neIndex, shelfIndex, slotIndex,
            cmL3FlowPointPortIndex, cmL3FlowPointIndex,  
            cmL3QosShaperIndex }
    ::= { cmL3QosShaperTable 1 }

CML3QosShaperEntry ::= SEQUENCE {
    cmL3QosShaperIndex               Integer32,
    cmL3QosShaperAdminState          AdminState,
    cmL3QosShaperOperationalState    OperationalState,
    cmL3QosShaperSecondaryState      SecondaryState,
    cmL3QosShaperCIRLo               Unsigned32,
    cmL3QosShaperCIRHi               Unsigned32,
    cmL3QosShaperEIRLo               Unsigned32,
    cmL3QosShaperEIRHi               Unsigned32,
    cmL3QosShaperBufferSize          Unsigned32,
    cmL3QosShaperCOS                 Integer32,
    cmL3QosShaperStorageType         StorageType,
    cmL3QosShaperRowStatus           RowStatus,
    cmL3QosShaperWfqWeight           Integer32
}

cmL3QosShaperIndex OBJECT-TYPE
    SYNTAX      Integer32 (1..8)
    MAX-ACCESS  read-create
    STATUS      current
    DESCRIPTION
            "The unique integer index value corresponding to a 
             Quality of Service Shaper."
    ::= { cmL3QosShaperEntry 1 }

-- State Management params
cmL3QosShaperAdminState OBJECT-TYPE
    SYNTAX      AdminState 
    MAX-ACCESS  read-write
    STATUS      current
    DESCRIPTION
            "This object represents the Administrative State of 
             the QOS Shaper." 
    ::= { cmL3QosShaperEntry 2 }

cmL3QosShaperOperationalState OBJECT-TYPE
    SYNTAX      OperationalState 
    MAX-ACCESS  read-only
    STATUS      current
    DESCRIPTION
            "This object represents the Operational State of the QOS Shaper." 
    ::= { cmL3QosShaperEntry 3 }

cmL3QosShaperSecondaryState OBJECT-TYPE
    SYNTAX      SecondaryState 
    MAX-ACCESS  read-only
    STATUS      current
    DESCRIPTION
            "This object represents the Secondary State of the QOS Shaper." 
    ::= { cmL3QosShaperEntry 4 }

cmL3QosShaperCIRLo OBJECT-TYPE
    SYNTAX     Unsigned32
    MAX-ACCESS read-create
    STATUS     current
    DESCRIPTION
         "This object represents the Commited Information
          Rate(CIR) (Lower 32 bits)of a Shaper."
     ::= { cmL3QosShaperEntry 5 }

cmL3QosShaperCIRHi OBJECT-TYPE
    SYNTAX     Unsigned32
    MAX-ACCESS read-create
    STATUS     current
    DESCRIPTION
         "This object represents the Commited Information
          Rate(CIR) (Higher 32 bits) of a Shaper."
     ::= { cmL3QosShaperEntry 6 }

cmL3QosShaperEIRLo OBJECT-TYPE
    SYNTAX     Unsigned32
    MAX-ACCESS read-create
    STATUS     current
    DESCRIPTION
         "This object represents the Excess Information
          Rate(EIR) (Higher 32 bits) on the Shaper."
     ::= { cmL3QosShaperEntry 7 }

cmL3QosShaperEIRHi OBJECT-TYPE
    SYNTAX     Unsigned32
    MAX-ACCESS read-create
    STATUS     current
    DESCRIPTION
         "This object represents the Excess Information
          Rate(EIR) (Higher 32 bits) on the Shaper."
     ::= { cmL3QosShaperEntry 8 }

cmL3QosShaperBufferSize OBJECT-TYPE
    SYNTAX     Unsigned32
    MAX-ACCESS read-create
    STATUS     current
    DESCRIPTION
         "This object represents the Buffer Size of the Shaper."
     ::= { cmL3QosShaperEntry 9 }

cmL3QosShaperCOS OBJECT-TYPE
    SYNTAX     Integer32 (0..7)
    MAX-ACCESS read-only
    STATUS     current
    DESCRIPTION
            "This object provides the COS (Class of Service)
             value for the QOS Shaper."
    ::= { cmL3QosShaperEntry 10 }

cmL3QosShaperStorageType OBJECT-TYPE
    SYNTAX     StorageType
    MAX-ACCESS read-create
    STATUS     current
    DESCRIPTION
            "The type of storage configured for this entry."
    ::= { cmL3QosShaperEntry 11 }

cmL3QosShaperRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmL3QosShaperRowStatus supported are
            createAndGo(4) and destroy(6).  All mandatory attributes
            must be specified in a single SNMP SET request with
            cmL3QosShaperRowStatus value as createAndGo(4).
            Upon successful row creation, this object has a
            value of active(1).

            The cmL3QosShaperRowStatus object may be modified if
            the associated instance of this object is equal to active(1)."
    ::= { cmL3QosShaperEntry 12 }

cmL3QosShaperWfqWeight OBJECT-TYPE
    SYNTAX     Integer32
    MAX-ACCESS read-write
    STATUS     current
    DESCRIPTION
            "This object represents the wfq weight of the QoS Shaper."
     ::= { cmL3QosShaperEntry 13 }

--
--  Traffic OSPF Interface Table
--
f3L3TrafficOspfInterfaceTable  OBJECT-TYPE
    SYNTAX      SEQUENCE OF F3L3TrafficOspfInterfaceEntry
    MAX-ACCESS  not-accessible
    STATUS      current
    DESCRIPTION
            "A list of entries for the Traffic OSPF Interface."
    ::= { f3L3Objects 36 }

f3L3TrafficOspfInterfaceEntry  OBJECT-TYPE
    SYNTAX      F3L3TrafficOspfInterfaceEntry
    MAX-ACCESS  not-accessible
    STATUS      current
    DESCRIPTION
            "A conceptual row in the f3L3TrafficOspfInterfaceTable."
    INDEX { neIndex,
            f3VrfIndex,
            f3VrfOspfRouterIndex,
            f3L3TrafficOspfAreaIndex,
            f3L3TrafficOspfInterfaceIndex }
    ::= { f3L3TrafficOspfInterfaceTable 1 }

F3L3TrafficOspfInterfaceEntry ::= SEQUENCE {
    f3L3TrafficOspfInterfaceIndex                               Integer32,
    f3L3TrafficOspfInterfaceOspfCost                            Unsigned32,
    f3L3TrafficOspfInterfaceType                                OspfIfType,
    f3L3TrafficOspfInterfaceOspfRtrPriority                     Integer32,
    f3L3TrafficOspfInterfaceOspfHelloInterval                   Integer32,
    f3L3TrafficOspfInterfaceOspfDeadInterval                    Integer32,
    f3L3TrafficOspfInterfaceOspfTransmitDelay                   Integer32,
    f3L3TrafficOspfInterfaceOspfRetransmitInterval              Integer32,
    f3L3TrafficOspfInterfaceState                               OspfInterfaceState,
    f3L3TrafficOspfInterfaceOspfDesignatedRouterId              IpAddress,
    f3L3TrafficOspfInterfaceOspfBackupDesignatedRouterId        IpAddress,
    f3L3TrafficOspfInterfaceOspfAuthType                        OspfAuthType,
    f3L3TrafficOspfInterfaceOspfSimpleAuthKey                   DisplayString,
    f3L3TrafficOspfInterfaceOspfCryptoKeyId                     VariablePointer,
    f3L3TrafficOspfInterfaceOspfInstanceId                      Unsigned32,
    f3L3TrafficOspfInterfaceId                                  Unsigned32,
    f3L3TrafficOspfInterfaceLinkLsaSuppression                  TruthValue,
    f3L3TrafficOspfInterfacePassiveControl                      TruthValue,
    f3L3TrafficOspfInterfaceAssociatedIpInterface               DisplayString,
    f3L3TrafficOspfInterfaceStorageType                         StorageType,
    f3L3TrafficOspfInterfaceRowStatus                           RowStatus,
    f3L3TrafficOspfInterfaceTilfaControl                        TruthValue,
    f3L3TrafficOspfInterfaceTilfaProtectionType                 TilfaProtectionType
}

f3L3TrafficOspfInterfaceIndex OBJECT-TYPE
    SYNTAX      Integer32
    MAX-ACCESS  not-accessible
    STATUS      current
    DESCRIPTION
           "The index of the Traffic OSPF Interface entry."
    ::= { f3L3TrafficOspfInterfaceEntry 1 }

f3L3TrafficOspfInterfaceOspfCost OBJECT-TYPE
    SYNTAX      Unsigned32
    MAX-ACCESS  read-write
    STATUS      current
    DESCRIPTION
            "The cost of the route during the SPF calculation."
    ::= { f3L3TrafficOspfInterfaceEntry 2 }

f3L3TrafficOspfInterfaceType OBJECT-TYPE
    SYNTAX      OspfIfType
    MAX-ACCESS  read-write
    STATUS      current
    DESCRIPTION
            "Interface network type."
    ::= { f3L3TrafficOspfInterfaceEntry 3 }

f3L3TrafficOspfInterfaceOspfRtrPriority OBJECT-TYPE
    SYNTAX      Integer32
    MAX-ACCESS  read-write
    STATUS      current
    DESCRIPTION
            "An 8-bit unsigned integer, used for DR and BDR election,
             may be default. 0 means not to attend DR election."
    ::= { f3L3TrafficOspfInterfaceEntry 4 }

f3L3TrafficOspfInterfaceOspfHelloInterval OBJECT-TYPE
    SYNTAX      Integer32
    MAX-ACCESS  read-write
    STATUS      current
    DESCRIPTION
            "The interval in seconds between Hello Packets
             that the router sends on the interface."
    ::= { f3L3TrafficOspfInterfaceEntry 5 }

f3L3TrafficOspfInterfaceOspfDeadInterval OBJECT-TYPE
    SYNTAX      Integer32
    MAX-ACCESS  read-write
    STATUS      current
    DESCRIPTION
            "The number of seconds before the router's neighbors
             will declare it down, when they stop hearing
             the router's Hello Packets."
    ::= { f3L3TrafficOspfInterfaceEntry 6 }

f3L3TrafficOspfInterfaceOspfTransmitDelay OBJECT-TYPE
    SYNTAX      Integer32
    MAX-ACCESS  read-write
    STATUS      current
    DESCRIPTION
            "The estimated number of seconds it takes to
             transmit a Link State Update Packet over this
             interface. LSAs contained in the Link State
             update packet will have their age incremented
             by this amount before transmission. This value
             should take into account transmission and
             propagation delays; it must be greater than zero."
    ::= { f3L3TrafficOspfInterfaceEntry 7 }

f3L3TrafficOspfInterfaceOspfRetransmitInterval OBJECT-TYPE
    SYNTAX      Integer32
    MAX-ACCESS  read-write
    STATUS      current
    DESCRIPTION
            "The number of seconds between LSA retransmissions,
            for adjacencies belonging to this interface.
            Also used when retransmitting Database Description
            and Link State Request Packets."
    ::= { f3L3TrafficOspfInterfaceEntry 8 }

f3L3TrafficOspfInterfaceState OBJECT-TYPE
    SYNTAX      OspfInterfaceState
    MAX-ACCESS  read-only
    STATUS      current
    DESCRIPTION
            "The State of Interface in running OSPF protocol."
    ::= { f3L3TrafficOspfInterfaceEntry 9 }

f3L3TrafficOspfInterfaceOspfDesignatedRouterId OBJECT-TYPE
    SYNTAX      IpAddress
    MAX-ACCESS  read-only
    STATUS      current
    DESCRIPTION
            "Designated Router IP interface on the Network."
    ::= { f3L3TrafficOspfInterfaceEntry 10 }

f3L3TrafficOspfInterfaceOspfBackupDesignatedRouterId OBJECT-TYPE
    SYNTAX      IpAddress
    MAX-ACCESS  read-only
    STATUS      current
    DESCRIPTION
            "Backup Designated Router IP interface on the Network."
    ::= { f3L3TrafficOspfInterfaceEntry 11 }

f3L3TrafficOspfInterfaceOspfAuthType OBJECT-TYPE
    SYNTAX      OspfAuthType
    MAX-ACCESS  read-write
    STATUS      current
    DESCRIPTION
            "This attribute is used to specify authentication type.
                Simple: 64-bits clear password inserted into ospf packets header.
                None: No authentication is used.
                Cryptographic: a shared secret which enables the
                    generation/verification of message digests which are
                    appended to the OSPF protocol packets.
                IPsec: use IP layer's IPSec to support authentication,
                    rather than OSPF header.."
    ::= { f3L3TrafficOspfInterfaceEntry 12 }

f3L3TrafficOspfInterfaceOspfSimpleAuthKey OBJECT-TYPE
    SYNTAX      DisplayString
    MAX-ACCESS  read-write
    STATUS      current
    DESCRIPTION
            "Simple Authentication type authentication key (8 Bytes length)."
    ::= { f3L3TrafficOspfInterfaceEntry 13 }

f3L3TrafficOspfInterfaceOspfCryptoKeyId OBJECT-TYPE
    SYNTAX      VariablePointer
    MAX-ACCESS  read-write
    STATUS      current
    DESCRIPTION
            "Key id from the keys configured in the Authentication keys table.
             This key is used if Authentication Type is cryptographic."
    ::= { f3L3TrafficOspfInterfaceEntry 14 }

f3L3TrafficOspfInterfaceOspfInstanceId OBJECT-TYPE
    SYNTAX      Unsigned32
    MAX-ACCESS  read-write
    STATUS      current
    DESCRIPTION
            "OSPFv3 Instance ID.  Instance ID allows multiple OSPF protocol
             instances to be run on a single link.  Default value is 0.
             It is only necessary to assign a value other than 0
             on those links that will contain multiple separate
             communities of OSPF routers.  Only Applicable to ospfv3."
    ::= { f3L3TrafficOspfInterfaceEntry 15 }

f3L3TrafficOspfInterfaceId OBJECT-TYPE
    SYNTAX      Unsigned32
    MAX-ACCESS  read-write
    STATUS      current
    DESCRIPTION
            "32-bit number uniquely identifying this interface among the
             collection of this router's interfaces.  Shall be unique
             per router. Default vlaue shall be the last number of EID.
             Only applicable to OSPFv3."
    ::= { f3L3TrafficOspfInterfaceEntry 16 }

f3L3TrafficOspfInterfaceLinkLsaSuppression OBJECT-TYPE
    SYNTAX      TruthValue
    MAX-ACCESS  read-write
    STATUS      current
    DESCRIPTION
            "Indicates whether or not origination of a link-LSA is suppressed.
             In OSPFv3, link LSAs are generated for each link, announcing
             link-local IPv6 address of the router to its local neighbors.
             These are useless on PtP or PtMP networks and this option allows
             to suppress the link LSA origination for such interfaces.
             The attribute is ignored on other than PtP or PtMP interfaces.
             Default value is disbaled.  Only applicable to OSPFv3."
    ::= { f3L3TrafficOspfInterfaceEntry 17 }

f3L3TrafficOspfInterfacePassiveControl OBJECT-TYPE
    SYNTAX      TruthValue
    MAX-ACCESS  read-write
    STATUS      current
    DESCRIPTION
            "Enable/Disable passive interface - a passive interface's prefix
             will be advertised but no neighbor adjacencies will be formed
             on the interface.."
    ::= { f3L3TrafficOspfInterfaceEntry 18 }

f3L3TrafficOspfInterfaceAssociatedIpInterface OBJECT-TYPE
    SYNTAX      DisplayString
    MAX-ACCESS  read-create
    STATUS      current
    DESCRIPTION
            "The reference of Traffic IP Interface or loopback interface.
             It is the name of interface."
    ::= { f3L3TrafficOspfInterfaceEntry 19 }

f3L3TrafficOspfInterfaceStorageType OBJECT-TYPE
    SYNTAX      StorageType
    MAX-ACCESS  read-create
    STATUS      current
    DESCRIPTION
           "The type of storage configured for this entry."
    ::= { f3L3TrafficOspfInterfaceEntry 20 }

f3L3TrafficOspfInterfaceRowStatus OBJECT-TYPE
    SYNTAX      RowStatus
    MAX-ACCESS  read-create
    STATUS      current
    DESCRIPTION
           "The status of this row.
                An entry MUST NOT exist in the active state unless all
                objects in the entry have an appropriate value, as described
                in the description clause for each writable object.

                The values of f3L3TrafficOspfInterfaceRowStatus supported are
                createAndGo(4) and destroy(6).  All mandatory attributes
                must be specified in a single SNMP SET request with
                f3L3TrafficOspfInterfaceRowStatus value as createAndGo(4).
                Upon successful row creation, this object has a
                value of active(1).

                The f3L3TrafficOspfInterfaceRowStatus object may be modified if
                the associated instance of this object is equal to active(1)."
    ::= { f3L3TrafficOspfInterfaceEntry 21 }

f3L3TrafficOspfInterfaceTilfaControl OBJECT-TYPE
    SYNTAX      TruthValue
    MAX-ACCESS  read-create
    STATUS      current
    DESCRIPTION
           "TI-LFA Control."
    ::= { f3L3TrafficOspfInterfaceEntry 22 }

f3L3TrafficOspfInterfaceTilfaProtectionType OBJECT-TYPE
    SYNTAX      TilfaProtectionType
    MAX-ACCESS  read-create
    STATUS      current
    DESCRIPTION
           "TI-LFA Protection Type."
    ::= { f3L3TrafficOspfInterfaceEntry 23 }

--
--  Traffic BGP Peer Address Family Table
--

f3L3TrafficBgpPeerAddressFamilyTable  OBJECT-TYPE
    SYNTAX      SEQUENCE OF F3L3TrafficBgpPeerAddressFamilyEntry
    MAX-ACCESS  not-accessible
    STATUS      current
    DESCRIPTION
            "A list of entries for the Traffic BGP Peer Address Family."
    ::= { f3L3Objects 37 }

f3L3TrafficBgpPeerAddressFamilyEntry  OBJECT-TYPE
    SYNTAX      F3L3TrafficBgpPeerAddressFamilyEntry
    MAX-ACCESS  not-accessible
    STATUS      current
    DESCRIPTION
            "A conceptual row in the f3L3TrafficBgpPeerAddressFamilyTable."
    INDEX { neIndex,
            f3VrfIndex,
            f3L3TrafficBgpRouterIndex,
            f3L3TrafficBgpPeerIndex,
            f3L3TrafficBgpPeerAddressFamilyIndex }
    ::= { f3L3TrafficBgpPeerAddressFamilyTable 1 }

F3L3TrafficBgpPeerAddressFamilyEntry ::= SEQUENCE {
    f3L3TrafficBgpPeerAddressFamilyIndex                              Integer32,
    f3L3TrafficBgpPeerAddressFamilyName                               BgpPeerAddressFamilyNameType,
    f3L3TrafficBgpPeerAddressFamilyRedistOspfRoute                    TruthValue,
    f3L3TrafficBgpPeerAddressFamilyRedistConnectedRoute               TruthValue,
    f3L3TrafficBgpPeerAddressFamilyRedistStaticRoute                  TruthValue,
    f3L3TrafficBgpPeerAddressFamilyRedistDhcpRoute                    TruthValue,
    f3L3TrafficBgpPeerAddressFamilyRedistSlaacRoute                   TruthValue,
    f3L3TrafficBgpPeerAddressFamilySendDefaultRoute                   TruthValue,
    f3L3TrafficBgpPeerAddressFamilyNextHopType                        BgpNextHopUpdateType,
    f3L3TrafficBgpPeerAddressFamilyNextHopIpv4                        IpAddress,
    f3L3TrafficBgpPeerAddressFamilyNextHopIpv6                        Ipv6Address,
    f3L3TrafficBgpPeerAddressFamilyExtNextHopControl                  TruthValue,
    f3L3TrafficBgpPeerAddressFamilyStorageType                        StorageType,
    f3L3TrafficBgpPeerAddressFamilyRowStatus                          RowStatus
}

f3L3TrafficBgpPeerAddressFamilyIndex OBJECT-TYPE
    SYNTAX      Integer32
    MAX-ACCESS  not-accessible
    STATUS      current
    DESCRIPTION
           "The index of the Traffic BGP Peer Address Family entry."
    ::= { f3L3TrafficBgpPeerAddressFamilyEntry 1 }

f3L3TrafficBgpPeerAddressFamilyName OBJECT-TYPE
    SYNTAX      BgpPeerAddressFamilyNameType
    MAX-ACCESS  read-create
    STATUS      current
    DESCRIPTION
           "Address Family Name."
    ::= { f3L3TrafficBgpPeerAddressFamilyEntry 2 }

f3L3TrafficBgpPeerAddressFamilyRedistOspfRoute OBJECT-TYPE
    SYNTAX      TruthValue
    MAX-ACCESS  read-write
    STATUS      current
    DESCRIPTION
           "If set to true, redistribute the connected route to the neighbour."
    ::= { f3L3TrafficBgpPeerAddressFamilyEntry 3 }

f3L3TrafficBgpPeerAddressFamilyRedistConnectedRoute OBJECT-TYPE
    SYNTAX      TruthValue
    MAX-ACCESS  read-write
    STATUS      current
    DESCRIPTION
           "If set to true, redistribute the connected route to the neighbour."
    ::= { f3L3TrafficBgpPeerAddressFamilyEntry 4 }

f3L3TrafficBgpPeerAddressFamilyRedistStaticRoute OBJECT-TYPE
    SYNTAX      TruthValue
    MAX-ACCESS  read-write
    STATUS      current
    DESCRIPTION
           "If set to true, redistribute the static route to the neighbour."
    ::= { f3L3TrafficBgpPeerAddressFamilyEntry 5 }

f3L3TrafficBgpPeerAddressFamilyRedistDhcpRoute OBJECT-TYPE
    SYNTAX      TruthValue
    MAX-ACCESS  read-write
    STATUS      current
    DESCRIPTION
           "If set to true, redistribute the dhcproute to the neighbour."
    ::= { f3L3TrafficBgpPeerAddressFamilyEntry 6 }

f3L3TrafficBgpPeerAddressFamilyRedistSlaacRoute OBJECT-TYPE
    SYNTAX      TruthValue
    MAX-ACCESS  read-write
    STATUS      current
    DESCRIPTION
           "If set to true, redistribute the default route to the neighbour.
            This attribute is only applicable to IPv6 address family."
    ::= { f3L3TrafficBgpPeerAddressFamilyEntry 7 }

f3L3TrafficBgpPeerAddressFamilySendDefaultRoute OBJECT-TYPE
    SYNTAX      TruthValue
    MAX-ACCESS  read-write
    STATUS      current
    DESCRIPTION
           "If set to true, send the default route to the neighbour."
    ::= { f3L3TrafficBgpPeerAddressFamilyEntry 8 }

f3L3TrafficBgpPeerAddressFamilyNextHopType OBJECT-TYPE
    SYNTAX      BgpNextHopUpdateType
    MAX-ACCESS  read-write
    STATUS      current
    DESCRIPTION
           "The mechanism to update NEXT HOP attribute in update message:
            1. DEFAULT: Update next hop according the rules in RFC4271
            2. SELF: Use transmitting interface's as the next hop
            3. IPv4 Address: Configure IPv4 address as next hop explicitly
            4. IPv6 Address: Configure IPv6 address as next hop explicitly"
    ::= { f3L3TrafficBgpPeerAddressFamilyEntry 9 }

f3L3TrafficBgpPeerAddressFamilyNextHopIpv4 OBJECT-TYPE
    SYNTAX      IpAddress
    MAX-ACCESS  read-write
    STATUS      current
    DESCRIPTION
           "The IPv4 address used to override NEXT HOP attribute."
    ::= { f3L3TrafficBgpPeerAddressFamilyEntry 10 }

f3L3TrafficBgpPeerAddressFamilyNextHopIpv6 OBJECT-TYPE
    SYNTAX      Ipv6Address
    MAX-ACCESS  read-write
    STATUS      current
    DESCRIPTION
           "The IPv4 address used to override NEXT HOP attribute."
    ::= { f3L3TrafficBgpPeerAddressFamilyEntry 11 }

f3L3TrafficBgpPeerAddressFamilyExtNextHopControl OBJECT-TYPE
    SYNTAX      TruthValue
    MAX-ACCESS  read-write
    STATUS      current
    DESCRIPTION
           "Whether to support Extended Next Hop
            Encoding Capability. E.g Allowing
            advertising IPV4 route with a Next Hop
            address of IPv6.."
    ::= { f3L3TrafficBgpPeerAddressFamilyEntry 12 }

f3L3TrafficBgpPeerAddressFamilyStorageType OBJECT-TYPE
    SYNTAX      StorageType
    MAX-ACCESS  read-create
    STATUS      current
    DESCRIPTION
           "The type of storage configured for this entry."
    ::= { f3L3TrafficBgpPeerAddressFamilyEntry 13 }

f3L3TrafficBgpPeerAddressFamilyRowStatus OBJECT-TYPE
    SYNTAX      RowStatus
    MAX-ACCESS  read-create
    STATUS      current
    DESCRIPTION
           "The status of this row.
                An entry MUST NOT exist in the active state unless all
                objects in the entry have an appropriate value, as described
                in the description clause for each writable object.

                The values of f3L3TrafficBgpPeerAddressFamilyRowStatus supported are
                createAndGo(4) and destroy(6).  All mandatory attributes
                must be specified in a single SNMP SET request with
                f3L3TrafficBgpPeerAddressFamilyRowStatus value as createAndGo(4).
                Upon successful row creation, this object has a
                value of active(1).

                The f3L3TrafficBgpPeerAddressFamilyRowStatus object may be modified if
                the associated instance of this object is equal to active(1)."
    ::= { f3L3TrafficBgpPeerAddressFamilyEntry 14 }

--
--  Traffic BGP RIB Route Table
--
f3L3TrafficBgpRIBRouteTable  OBJECT-TYPE
    SYNTAX      SEQUENCE OF F3L3TrafficBgpRIBRouteEntry
    MAX-ACCESS  not-accessible
    STATUS      current
    DESCRIPTION
            "A list of entries for the Traffic BGP RIB routes."
    ::= { f3L3Objects 38 }

f3L3TrafficBgpRIBRouteEntry  OBJECT-TYPE
    SYNTAX      F3L3TrafficBgpRIBRouteEntry
    MAX-ACCESS  not-accessible
    STATUS      current
    DESCRIPTION
            "A conceptual row in the f3L3TrafficBgpRouteTable."
    INDEX { neIndex,
            f3VrfIndex,
            f3L3TrafficBgpRouterIndex,
            f3L3TrafficBgpRIBRouteIndex }
    ::= { f3L3TrafficBgpRIBRouteTable 1 }

F3L3TrafficBgpRIBRouteEntry ::= SEQUENCE {
    f3L3TrafficBgpRIBRouteIndex         Integer32,
    f3L3TrafficBgpRIBRouteNetwork       DisplayString,
    f3L3TrafficBgpRIBRouteNextHop       DisplayString,
    f3L3TrafficBgpRIBRouteMetric        Integer32,
    f3L3TrafficBgpRIBRoutePath          DisplayString
}

f3L3TrafficBgpRIBRouteIndex OBJECT-TYPE
    SYNTAX      Integer32
    MAX-ACCESS  not-accessible
    STATUS      current
    DESCRIPTION
           "The index of the Traffic BGP RIB Route entry."
    ::= { f3L3TrafficBgpRIBRouteEntry 1 }

f3L3TrafficBgpRIBRouteNetwork OBJECT-TYPE
    SYNTAX      DisplayString
    MAX-ACCESS  read-only
    STATUS      current
    DESCRIPTION
           "Traffic BGP RIB Route's destination network address."
    ::= { f3L3TrafficBgpRIBRouteEntry 2 }

f3L3TrafficBgpRIBRouteNextHop OBJECT-TYPE
    SYNTAX      DisplayString
    MAX-ACCESS  read-only
    STATUS      current
    DESCRIPTION
           "Traffic BGP RIB Route's next hop interface address."
    ::= { f3L3TrafficBgpRIBRouteEntry 3 }

f3L3TrafficBgpRIBRouteMetric OBJECT-TYPE
    SYNTAX      Integer32
    MAX-ACCESS  read-only
    STATUS      current
    DESCRIPTION
           "List of AS numbers in the path to route's destination network"
    ::= { f3L3TrafficBgpRIBRouteEntry 4 }

f3L3TrafficBgpRIBRoutePath OBJECT-TYPE
    SYNTAX      DisplayString
    MAX-ACCESS  read-only
    STATUS      current
    DESCRIPTION
           "The index of the Traffic BGP RIB Route entry."
    ::= { f3L3TrafficBgpRIBRouteEntry 5 }

--
--  L3 Traffic BGP In Route Table 
--

f3L3TrafficBgpInRouteTable  OBJECT-TYPE
    SYNTAX      SEQUENCE OF F3L3TrafficBgpInRouteEntry
    MAX-ACCESS  not-accessible
    STATUS      current
    DESCRIPTION
            "BGP In routes.
             Must set f3L3TrafficBgpRouterAction as optimizeBgpInRouteRetrieve(2) before get data from this table."
    ::= { f3L3Objects 39 }

f3L3TrafficBgpInRouteEntry OBJECT-TYPE
    SYNTAX      F3L3TrafficBgpInRouteEntry 
    MAX-ACCESS  not-accessible
    STATUS      current
    DESCRIPTION
            "A conceptual row in the f3L3TrafficBgpInRouteTable. Entries can
            be created/deleted in this table by management application action."
    INDEX { neIndex, 
            f3VrfIndex, 
            f3L3TrafficBgpRouterIndex,
            f3L3TrafficBgpInRouteIndex }
    ::= { f3L3TrafficBgpInRouteTable 1 }

F3L3TrafficBgpInRouteEntry ::= SEQUENCE {
    f3L3TrafficBgpInRouteIndex                     Unsigned32,
    f3L3TrafficBgpInRouteNetwork                   DisplayString,
    f3L3TrafficBgpInRouteNextHop                   DisplayString,
    f3L3TrafficBgpInRouteMetric                    Unsigned32,
    f3L3TrafficBgpInRoutePath                      DisplayString,
    f3L3TrafficBgpInRouteLocalPreference           Unsigned32
}

f3L3TrafficBgpInRouteIndex OBJECT-TYPE
    SYNTAX      Unsigned32
    MAX-ACCESS  not-accessible
    STATUS      current
    DESCRIPTION
        "Index of this route. Key of the table."
   ::= { f3L3TrafficBgpInRouteEntry 1 }

f3L3TrafficBgpInRouteNetwork OBJECT-TYPE
    SYNTAX      DisplayString (SIZE(0..64))
    MAX-ACCESS  read-only
    STATUS      current
    DESCRIPTION
        "Network of destination."
   ::= { f3L3TrafficBgpInRouteEntry 2 }
   
f3L3TrafficBgpInRouteNextHop OBJECT-TYPE
    SYNTAX      DisplayString (SIZE(0..64))
    MAX-ACCESS  read-only
    STATUS      current
    DESCRIPTION
        "Address of next hop."
   ::= { f3L3TrafficBgpInRouteEntry 3 }

f3L3TrafficBgpInRouteMetric OBJECT-TYPE
    SYNTAX      Unsigned32
    MAX-ACCESS  read-only
    STATUS      current
    DESCRIPTION
        "Metric value of this route."
   ::= { f3L3TrafficBgpInRouteEntry 4 }

f3L3TrafficBgpInRoutePath OBJECT-TYPE
    SYNTAX      DisplayString (SIZE(0..1024))
    MAX-ACCESS  read-only
    STATUS      current
    DESCRIPTION
        "The list of AS numbers to the destination."
   ::= { f3L3TrafficBgpInRouteEntry 5 }

f3L3TrafficBgpInRouteLocalPreference OBJECT-TYPE
    SYNTAX      Unsigned32
    MAX-ACCESS  read-only
    STATUS      current
    DESCRIPTION
        "Local Preference Value received from iBGP."
   ::= { f3L3TrafficBgpInRouteEntry 6 }

--
--  L3 Traffic BGP Route V2 Table 
--

f3L3TrafficBgpRouteV2Table  OBJECT-TYPE
    SYNTAX      SEQUENCE OF F3L3TrafficBgpRouteV2Entry
    MAX-ACCESS  not-accessible
    STATUS      current
    DESCRIPTION
            "BGP routes.
             Must set f3L3TrafficBgpRouterAction as optimizeBgpRouteRetrieve(1) before get data from this table."
    ::= { f3L3Objects 40 }

f3L3TrafficBgpRouteV2Entry OBJECT-TYPE
    SYNTAX      F3L3TrafficBgpRouteV2Entry 
    MAX-ACCESS  not-accessible
    STATUS      current
    DESCRIPTION
            "A conceptual row in the f3L3TrafficBgpRouteV2Table. Entries can
            be created/deleted in this table by management application action."
    INDEX { neIndex, 
            f3VrfIndex, 
            f3L3TrafficBgpRouterIndex,
            f3L3TrafficBgpRouteV2Index }
    ::= { f3L3TrafficBgpRouteV2Table 1 }

F3L3TrafficBgpRouteV2Entry ::= SEQUENCE {
    f3L3TrafficBgpRouteV2Index                     Unsigned32,
    f3L3TrafficBgpRouteV2Network                   DisplayString,
    f3L3TrafficBgpRouteV2NextHop                   DisplayString,
    f3L3TrafficBgpRouteV2Metric                    Unsigned32,
    f3L3TrafficBgpRouteV2Path                      DisplayString,
    f3L3TrafficBgpRouteV2LocalPreference           Unsigned32
}

f3L3TrafficBgpRouteV2Index OBJECT-TYPE
    SYNTAX      Unsigned32
    MAX-ACCESS  not-accessible
    STATUS      current
    DESCRIPTION
        "Index of this route. Key of the table."
   ::= { f3L3TrafficBgpRouteV2Entry 1 }

f3L3TrafficBgpRouteV2Network OBJECT-TYPE
    SYNTAX      DisplayString (SIZE(0..64))
    MAX-ACCESS  read-only
    STATUS      current
    DESCRIPTION
        "Network of destination."
   ::= { f3L3TrafficBgpRouteV2Entry 2 }
   
f3L3TrafficBgpRouteV2NextHop OBJECT-TYPE
    SYNTAX      DisplayString (SIZE(0..64))
    MAX-ACCESS  read-only
    STATUS      current
    DESCRIPTION
        "Address of next hop."
   ::= { f3L3TrafficBgpRouteV2Entry 3 }

f3L3TrafficBgpRouteV2Metric OBJECT-TYPE
    SYNTAX      Unsigned32
    MAX-ACCESS  read-only
    STATUS      current
    DESCRIPTION
        "Metric value of this route."
   ::= { f3L3TrafficBgpRouteV2Entry 4 }

f3L3TrafficBgpRouteV2Path OBJECT-TYPE
    SYNTAX      DisplayString (SIZE(0..1024))
    MAX-ACCESS  read-only
    STATUS      current
    DESCRIPTION
        "The list of AS numbers to the destination."
   ::= { f3L3TrafficBgpRouteV2Entry 5 }

f3L3TrafficBgpRouteV2LocalPreference OBJECT-TYPE
    SYNTAX      Unsigned32
    MAX-ACCESS  read-only
    STATUS      current
    DESCRIPTION
        "Local Preference Value received from iBGP."
   ::= { f3L3TrafficBgpRouteV2Entry 6 }


--
--  L3 Traffic BGP Peer Address Family Advertising Prefix Table 
--

f3L3TrafficBgpPeerAddressFamilyAdvPrefixTable  OBJECT-TYPE
    SYNTAX      SEQUENCE OF F3L3TrafficBgpPeerAddressFamilyAdvPrefixEntry
    MAX-ACCESS  not-accessible
    STATUS      current
    DESCRIPTION
            "Advertising Prefix of BGP Peer Address Family."
    ::= { f3L3Objects 41 }

f3L3TrafficBgpPeerAddressFamilyAdvPrefixEntry OBJECT-TYPE
    SYNTAX      F3L3TrafficBgpPeerAddressFamilyAdvPrefixEntry 
    MAX-ACCESS  not-accessible
    STATUS      current
    DESCRIPTION
            "A conceptual row in the f3L3TrafficBgpPeerAddressFamilyAdvPrefixTable. Entries can
            be created/deleted in this table by management application action."
    INDEX { neIndex, 
            f3VrfIndex, 
            f3L3TrafficBgpRouterIndex,
            f3L3TrafficBgpPeerIndex,
            f3L3TrafficBgpPeerAddressFamilyIndex,
            f3L3TrafficBgpPeerAddressFamilyAdvPrefix }
    ::= { f3L3TrafficBgpPeerAddressFamilyAdvPrefixTable 1 }

F3L3TrafficBgpPeerAddressFamilyAdvPrefixEntry ::= SEQUENCE {
    f3L3TrafficBgpPeerAddressFamilyAdvPrefix                     DisplayString,
    f3L3TrafficBgpPeerAddressFamilyAdvPrefixStorageType          StorageType,
    f3L3TrafficBgpPeerAddressFamilyAdvPrefixRowStatus            RowStatus
}

f3L3TrafficBgpPeerAddressFamilyAdvPrefix OBJECT-TYPE
    SYNTAX      DisplayString
    MAX-ACCESS  not-accessible
    STATUS      current
    DESCRIPTION
        "Advertising Prefix of a BGP Peer Address Family. Key of the table."
   ::= { f3L3TrafficBgpPeerAddressFamilyAdvPrefixEntry 1 }

f3L3TrafficBgpPeerAddressFamilyAdvPrefixStorageType OBJECT-TYPE
    SYNTAX      StorageType
    MAX-ACCESS  read-create
    STATUS      current
    DESCRIPTION
        "The storage type for this conceptual row."
   ::= { f3L3TrafficBgpPeerAddressFamilyAdvPrefixEntry 2 }

f3L3TrafficBgpPeerAddressFamilyAdvPrefixRowStatus OBJECT-TYPE
    SYNTAX      RowStatus
    MAX-ACCESS  read-create
    STATUS      current
    DESCRIPTION
        "The status of this row.  An entry MUST NOT exist in the 
        active state unless all objects in the entry have an 
        appropriate value, as described
        in the description clause for each writable object.

        The values of f3L3TrafficBgpPeerAddressFamilyAdvPrefixRowStatus supported are
        createAndGo(4) and destroy(6).  All mandatory attributes
        must be specified in a single SNMP SET request with
        f3L3TrafficBgpPeerAddressFamilyAdvPrefixRowStatus value as createAndGo(4).
        Upon successful row creation, this object has a
        value of active(1).

        The f3L3TrafficBgpPeerAddressFamilyAdvPrefixRowStatus object may be modified if
        the associated instance of this object is equal to active(1)."
   ::= { f3L3TrafficBgpPeerAddressFamilyAdvPrefixEntry 3 }


--
--  L3 Traffic Ospf v3 Neighbor
--

f3L3TrafficOspfV3NeighborTable  OBJECT-TYPE
    SYNTAX      SEQUENCE OF F3L3TrafficOspfV3NeighborEntry
    MAX-ACCESS  not-accessible
    STATUS      current
    DESCRIPTION
            "OSPF v3 neighbor table.
             Must set f3VrfOspfRouterAction as optimizeOspfNeighborRetrieve(3) before get data from this table."
    ::= { f3L3Objects 42 }

f3L3TrafficOspfV3NeighborEntry OBJECT-TYPE
    SYNTAX      F3L3TrafficOspfV3NeighborEntry 
    MAX-ACCESS  not-accessible
    STATUS      current
    DESCRIPTION
            "A conceptual row in the f3L3TrafficOspfV3NeighborTable. Entries can
            be created/deleted in this table by management application action."
    INDEX { neIndex, 
            f3VrfIndex,
            f3VrfOspfRouterIndex,
            f3L3TrafficOspfV3NeighborRouterId,
            f3L3TrafficOspfV3NeighborInterfaceId }
    ::= { f3L3TrafficOspfV3NeighborTable 1 }

F3L3TrafficOspfV3NeighborEntry ::= SEQUENCE {
    f3L3TrafficOspfV3NeighborRouterId                 IpAddress,
    f3L3TrafficOspfV3NeighborInterfaceId              Unsigned32,
    f3L3TrafficOspfV3NeighborPriority                 Unsigned32,
    f3L3TrafficOspfV3NeighborDeadTime                 Unsigned32,
    f3L3TrafficOspfV3NeighborLocalInterfaceName       DisplayString,
    f3L3TrafficOspfV3NeighborState                    OspfAdjacencyState,
    f3L3TrafficOspfV3NeighborRole                     TrafficOspfRole,
    f3L3TrafficOspfV3NeighborIpAddress                DisplayString
}

f3L3TrafficOspfV3NeighborRouterId OBJECT-TYPE
    SYNTAX      IpAddress
    MAX-ACCESS  read-only
    STATUS      current
    DESCRIPTION
        "Router ID of the neighbor."
   ::= { f3L3TrafficOspfV3NeighborEntry 1 }

f3L3TrafficOspfV3NeighborInterfaceId OBJECT-TYPE
    SYNTAX      Unsigned32
    MAX-ACCESS  read-only
    STATUS      current
    DESCRIPTION
        "ID of the interface of neighbor."
   ::= { f3L3TrafficOspfV3NeighborEntry 2 }

f3L3TrafficOspfV3NeighborPriority OBJECT-TYPE
    SYNTAX      Unsigned32
    MAX-ACCESS  read-only
    STATUS      current
    DESCRIPTION
        "The priority of the neighbor."
   ::= { f3L3TrafficOspfV3NeighborEntry 3 }

f3L3TrafficOspfV3NeighborDeadTime OBJECT-TYPE
    SYNTAX      Unsigned32
    MAX-ACCESS  read-only
    STATUS      current
    DESCRIPTION
        "The Dead Time field indicates the amount of time remaining 
        that the router waits to receive an OSPF hello packet from 
        the neighbor before declaring the neighbor down."
   ::= { f3L3TrafficOspfV3NeighborEntry 4 }

f3L3TrafficOspfV3NeighborLocalInterfaceName OBJECT-TYPE
    SYNTAX      DisplayString
    MAX-ACCESS  read-only
    STATUS      current
    DESCRIPTION
        "The name of local interface which discovers the neighbor."
   ::= { f3L3TrafficOspfV3NeighborEntry 5 }

f3L3TrafficOspfV3NeighborState OBJECT-TYPE
    SYNTAX      OspfAdjacencyState
    MAX-ACCESS  read-only
    STATUS      current
    DESCRIPTION
        "State of Link State Database synchronization with the neighbor."
   ::= { f3L3TrafficOspfV3NeighborEntry 6 }

f3L3TrafficOspfV3NeighborRole OBJECT-TYPE
    SYNTAX      TrafficOspfRole
    MAX-ACCESS  read-only
    STATUS      current
    DESCRIPTION
        "Role of the neighbor. DR, DR other and Backup are applicable."
   ::= { f3L3TrafficOspfV3NeighborEntry 7 }

f3L3TrafficOspfV3NeighborIpAddress OBJECT-TYPE
    SYNTAX      DisplayString
    MAX-ACCESS  read-only
    STATUS      current
    DESCRIPTION
        "Link-local Address of interface of neighbor."
   ::= { f3L3TrafficOspfV3NeighborEntry 8 }


--
--  L3 Traffic Ospf Link Link State Database
--

f3L3TrafficOspfLinkLsDbTable  OBJECT-TYPE
    SYNTAX      SEQUENCE OF F3L3TrafficOspfLinkLsDbEntry
    MAX-ACCESS  not-accessible
    STATUS      current
    DESCRIPTION
            "OSPF Link State database.
             Must set f3VrfOspfRouterAction as optimizeOspfLinkLinkLsDbRetrieve(4) before get data from this table."
    ::= { f3L3Objects 43 }

f3L3TrafficOspfLinkLsDbEntry OBJECT-TYPE
    SYNTAX      F3L3TrafficOspfLinkLsDbEntry 
    MAX-ACCESS  not-accessible
    STATUS      current
    DESCRIPTION
            "A conceptual row in the f3L3TrafficOspfLinkLsDbTable. Entries can
            be created/deleted in this table by management application action."
    INDEX { neIndex, 
            f3VrfIndex, 
            f3VrfOspfRouterIndex,
            f3L3TrafficOspfLinkLsDbType,
            f3L3TrafficOspfLinkLsDbId,
            f3L3TrafficOspfLinkLsDbAdvRouterId,
            f3L3TrafficOspfLinkLsDbInterfaceId,
            f3L3TrafficOspfLinkLsDbInterface }
    ::= { f3L3TrafficOspfLinkLsDbTable 1 }

F3L3TrafficOspfLinkLsDbEntry ::= SEQUENCE {
    f3L3TrafficOspfLinkLsDbType                OspfLsaType,
    f3L3TrafficOspfLinkLsDbId                  IpAddress,
    f3L3TrafficOspfLinkLsDbAdvRouterId         IpAddress,
    f3L3TrafficOspfLinkLsDbInterfaceId         Unsigned32,
    f3L3TrafficOspfLinkLsDbInterface           DisplayString,
    f3L3TrafficOspfLinkLsDbAreaId              IpAddress,
    f3L3TrafficOspfLinkLsDbChecksum            Unsigned32,
    f3L3TrafficOspfLinkLsDbSeqNum              Unsigned32,
    f3L3TrafficOspfLinkLsDbAge                 Unsigned32,
    f3L3TrafficOspfLinkLsDbRtrPriority         Unsigned32,
    f3L3TrafficOspfLinkLsDbLinkLocalAddress    DisplayString,
    f3L3TrafficOspfLinkLsDbPrefixList          DisplayString
}

f3L3TrafficOspfLinkLsDbType OBJECT-TYPE
    SYNTAX      OspfLsaType
    MAX-ACCESS  not-accessible
    STATUS      current
    DESCRIPTION
        "LSA Type."
   ::= { f3L3TrafficOspfLinkLsDbEntry 1 }

f3L3TrafficOspfLinkLsDbId OBJECT-TYPE
    SYNTAX      IpAddress
    MAX-ACCESS  not-accessible
    STATUS      current
    DESCRIPTION
        "Link State ID."
   ::= { f3L3TrafficOspfLinkLsDbEntry 2 }

f3L3TrafficOspfLinkLsDbAdvRouterId OBJECT-TYPE
    SYNTAX      IpAddress
    MAX-ACCESS  not-accessible
    STATUS      current
    DESCRIPTION
        "Advertising Router ID."
   ::= { f3L3TrafficOspfLinkLsDbEntry 3 }

f3L3TrafficOspfLinkLsDbInterfaceId OBJECT-TYPE
    SYNTAX      Unsigned32
    MAX-ACCESS  not-accessible
    STATUS      current
    DESCRIPTION
        "The interface id of the interface instance from which the LSA was received."
   ::= { f3L3TrafficOspfLinkLsDbEntry 4 }

f3L3TrafficOspfLinkLsDbInterface OBJECT-TYPE
    SYNTAX      DisplayString
    MAX-ACCESS  not-accessible
    STATUS      current
    DESCRIPTION
        "The local interface name from which the LSA was received."
   ::= { f3L3TrafficOspfLinkLsDbEntry 5 }
   
f3L3TrafficOspfLinkLsDbAreaId OBJECT-TYPE
    SYNTAX      IpAddress
    MAX-ACCESS  read-only
    STATUS      current
    DESCRIPTION
        "Area ID."
   ::= { f3L3TrafficOspfLinkLsDbEntry 6 }

f3L3TrafficOspfLinkLsDbChecksum OBJECT-TYPE
    SYNTAX      Unsigned32
    MAX-ACCESS  read-only
    STATUS      current
    DESCRIPTION
        "The checksum associated with Link State Advertisement."
   ::= { f3L3TrafficOspfLinkLsDbEntry 7 }

f3L3TrafficOspfLinkLsDbSeqNum OBJECT-TYPE
    SYNTAX      Unsigned32
    MAX-ACCESS  read-only
    STATUS      current
    DESCRIPTION
        "The Sequence Number associated with the last LSA."
   ::= { f3L3TrafficOspfLinkLsDbEntry 8 }

f3L3TrafficOspfLinkLsDbAge OBJECT-TYPE
    SYNTAX      Unsigned32
    MAX-ACCESS  read-only
    STATUS      current
    DESCRIPTION
        "The age, in seconds, since this LSA was last received."
   ::= { f3L3TrafficOspfLinkLsDbEntry 9 }

f3L3TrafficOspfLinkLsDbRtrPriority OBJECT-TYPE
    SYNTAX      Unsigned32
    MAX-ACCESS  read-only
    STATUS      current
    DESCRIPTION
        "Router priority for the interface."
   ::= { f3L3TrafficOspfLinkLsDbEntry 10 }

f3L3TrafficOspfLinkLsDbLinkLocalAddress OBJECT-TYPE
    SYNTAX      DisplayString
    MAX-ACCESS  read-only
    STATUS      current
    DESCRIPTION
        "The originating router's linklocal interface address for the link."
   ::= { f3L3TrafficOspfLinkLsDbEntry 11 }

f3L3TrafficOspfLinkLsDbPrefixList OBJECT-TYPE
    SYNTAX      DisplayString
    MAX-ACCESS  read-only
    STATUS      current
    DESCRIPTION
        "List of Prefixes associated with the link. 
         In maximum, up to 16 prefixes are supported."
   ::= { f3L3TrafficOspfLinkLsDbEntry 12 }


--
--  L3 traffic ipv4 static route Table
--

f3L3TrafficIpv4StaticRouteTable  OBJECT-TYPE
    SYNTAX      SEQUENCE OF F3L3TrafficIpv4StaticRouteEntry
    MAX-ACCESS  not-accessible
    STATUS      current
    DESCRIPTION
            "A list of entries for the L3 Traffic Ipv4 Static route."
    ::= { f3L3Objects 44 }

f3L3TrafficIpv4StaticRouteEntry  OBJECT-TYPE
    SYNTAX      F3L3TrafficIpv4StaticRouteEntry
    MAX-ACCESS  not-accessible
    STATUS      current
    DESCRIPTION
            "A conceptual row in the f3L3TrafficIpv4StaticRouteTable."
    INDEX { neIndex, 
            f3VrfIndex, 
            f3L3TrafficIpv4StaticRouteDest, 
            f3L3TrafficIpv4StaticRouteMask, 
            f3L3TrafficIpv4StaticRouteNextHop, 
            f3L3TrafficIpv4StaticRouteInterface }
    ::= { f3L3TrafficIpv4StaticRouteTable 1 }

F3L3TrafficIpv4StaticRouteEntry ::= SEQUENCE {
    f3L3TrafficIpv4StaticRouteDest                                IpAddress,
    f3L3TrafficIpv4StaticRouteMask                                IpAddress,
    f3L3TrafficIpv4StaticRouteNextHop                             DisplayString,
    f3L3TrafficIpv4StaticRouteInterface                           DisplayString,
    f3L3TrafficIpv4StaticRouteMetric                              Integer32,
    f3L3TrafficIpv4StaticRouteSourceForwardingEnable              TruthValue,
    f3L3TrafficIpv4StaticRouteStorageType                         StorageType,
    f3L3TrafficIpv4StaticRouteRowStatus                           RowStatus
}

f3L3TrafficIpv4StaticRouteDest OBJECT-TYPE
    SYNTAX      IpAddress
    MAX-ACCESS  not-accessible
    STATUS      current
    DESCRIPTION
           "It specifies the traffic Ipv4 Static route destination."
    ::= { f3L3TrafficIpv4StaticRouteEntry 1 }

f3L3TrafficIpv4StaticRouteMask OBJECT-TYPE
    SYNTAX      IpAddress
    MAX-ACCESS  not-accessible
    STATUS      current
    DESCRIPTION
           "It specifies the traffic Ipv4 Static route mask."
    ::= { f3L3TrafficIpv4StaticRouteEntry 2 }

f3L3TrafficIpv4StaticRouteNextHop OBJECT-TYPE
    SYNTAX      DisplayString
    MAX-ACCESS  not-accessible
    STATUS      current
    DESCRIPTION
           "It specifies the traffic Ipv4 Static route next hop."
    ::= { f3L3TrafficIpv4StaticRouteEntry 3 }

f3L3TrafficIpv4StaticRouteInterface OBJECT-TYPE
    SYNTAX      DisplayString
    MAX-ACCESS  not-accessible
    STATUS      current
    DESCRIPTION
           "It specifies the traffic Ipv4 Static route interface."
    ::= { f3L3TrafficIpv4StaticRouteEntry 4 }

f3L3TrafficIpv4StaticRouteMetric OBJECT-TYPE
    SYNTAX      Integer32
    MAX-ACCESS  read-write
    STATUS      current
    DESCRIPTION
           "It specifies the traffic Ipv4 Static route metric."
    ::= { f3L3TrafficIpv4StaticRouteEntry 5 }

f3L3TrafficIpv4StaticRouteSourceForwardingEnable OBJECT-TYPE
    SYNTAX      TruthValue
    MAX-ACCESS  read-write
    STATUS      current
    DESCRIPTION
           "It specifies the traffic Ipv4 static route source forwarding whether enabled."
    ::= { f3L3TrafficIpv4StaticRouteEntry 6 }

f3L3TrafficIpv4StaticRouteStorageType OBJECT-TYPE
    SYNTAX      StorageType
    MAX-ACCESS  read-create
    STATUS      current
    DESCRIPTION
           "The type of storage configured for this entry."
    ::= { f3L3TrafficIpv4StaticRouteEntry 7 }

f3L3TrafficIpv4StaticRouteRowStatus OBJECT-TYPE
    SYNTAX      RowStatus
    MAX-ACCESS  read-create
    STATUS      current
    DESCRIPTION
           "The status of this row.
          	An entry MUST NOT exist in the active state unless all
          	objects in the entry have an appropriate value, as described
          	in the description clause for each writable object.
 	
          	The values of f3L3TrafficIpv4StaticRouteRowStatus supported are
          	createAndGo(4) and destroy(6).  All mandatory attributes
          	must be specified in a single SNMP SET request with
          	f3L3TrafficIpv4StaticRouteRowStatus value as createAndGo(4).
          	Upon successful row creation, this object has a
          	value of active(1).
 	
          	The f3L3TrafficIpv4StaticRouteRowStatus object may be modified if
          	the associated instance of this object is equal to active(1)."
    ::= { f3L3TrafficIpv4StaticRouteEntry 8 }

--
--  L3 taffic ipv4 all route Table
--
f3L3TrafficIpv4AllRouteTable  OBJECT-TYPE
    SYNTAX      SEQUENCE OF F3L3TrafficIpv4AllRouteEntry
    MAX-ACCESS  not-accessible
    STATUS      current
    DESCRIPTION
            "A list of entries for the L3 Traffic Ipv4 route.
             Must set f3VrfActionX as optimizeRouteRetrieve(3) before get data from this table."
    ::= { f3L3Objects 45 }

f3L3TrafficIpv4AllRouteEntry  OBJECT-TYPE
    SYNTAX      F3L3TrafficIpv4AllRouteEntry
    MAX-ACCESS  not-accessible
    STATUS      current
    DESCRIPTION
            "A conceptual row in the f3L3TrafficIpv4AllRouteTable."
    INDEX { neIndex, 
            f3VrfIndex, 
            f3L3TrafficIpv4AllRouteDest, 
            f3L3TrafficIpv4AllRouteMask, 
            f3L3TrafficIpv4AllRouteNextHop, 
            f3L3TrafficIpv4AllRouteInterface,
            f3L3TrafficIpv4AllRouteOrigin }
    ::= { f3L3TrafficIpv4AllRouteTable 1 }

F3L3TrafficIpv4AllRouteEntry ::= SEQUENCE {
    f3L3TrafficIpv4AllRouteDest                                IpAddress,
    f3L3TrafficIpv4AllRouteMask                                IpAddress,
    f3L3TrafficIpv4AllRouteNextHop                             DisplayString,
    f3L3TrafficIpv4AllRouteInterface                           DisplayString,
    f3L3TrafficIpv4AllRouteOrigin                              TrafficIpRouteOriginType,
    f3L3TrafficIpv4AllRouteMetric                              Integer32,
    f3L3TrafficIpv4AllRouteSourceForwardingEnable              TruthValue,
    f3L3TrafficIpv4AllRouteAdminDistance                       Unsigned32,
    f3L3TrafficIpv4AllRouteStatus                              TrafficIpRouteStatusType,
    f3L3TrafficIpv4AllRouteStorageType                         StorageType,
    f3L3TrafficIpv4AllRouteRowStatus                           RowStatus
}

f3L3TrafficIpv4AllRouteDest OBJECT-TYPE
    SYNTAX      IpAddress
    MAX-ACCESS  not-accessible
    STATUS      current
    DESCRIPTION
           "It specifies the traffic Ipv4 route destination."
    ::= { f3L3TrafficIpv4AllRouteEntry 1 }

f3L3TrafficIpv4AllRouteMask OBJECT-TYPE
    SYNTAX      IpAddress
    MAX-ACCESS  not-accessible
    STATUS      current
    DESCRIPTION
           "It specifies the traffic Ipv4 route mask."
    ::= { f3L3TrafficIpv4AllRouteEntry 2 }

f3L3TrafficIpv4AllRouteNextHop OBJECT-TYPE
    SYNTAX      DisplayString
    MAX-ACCESS  not-accessible
    STATUS      current
    DESCRIPTION
           "It specifies the traffic Ipv4 route next hop."
    ::= { f3L3TrafficIpv4AllRouteEntry 3 }

f3L3TrafficIpv4AllRouteInterface OBJECT-TYPE
    SYNTAX      DisplayString
    MAX-ACCESS  not-accessible
    STATUS      current
    DESCRIPTION
           "It specifies the traffic Ipv4 route interface."
    ::= { f3L3TrafficIpv4AllRouteEntry 4 }

f3L3TrafficIpv4AllRouteOrigin OBJECT-TYPE
    SYNTAX      TrafficIpRouteOriginType
    MAX-ACCESS  not-accessible
    STATUS      current
    DESCRIPTION
        "The origin of IP Route."
   ::= { f3L3TrafficIpv4AllRouteEntry 5 }

f3L3TrafficIpv4AllRouteMetric OBJECT-TYPE
    SYNTAX      Integer32
    MAX-ACCESS  read-write
    STATUS      current
    DESCRIPTION
           "It specifies the traffic Ipv4 route metric."
    ::= { f3L3TrafficIpv4AllRouteEntry 6 }

f3L3TrafficIpv4AllRouteSourceForwardingEnable OBJECT-TYPE
    SYNTAX      TruthValue
    MAX-ACCESS  read-write
    STATUS      current
    DESCRIPTION
           "It specifies the traffic Ipv4 route source forwarding whether enabled."
    ::= { f3L3TrafficIpv4AllRouteEntry 7 }

f3L3TrafficIpv4AllRouteAdminDistance OBJECT-TYPE
    SYNTAX      Unsigned32
    MAX-ACCESS  read-only
    STATUS      current
    DESCRIPTION
        "The Administrative Distance of IP Route."
   ::= { f3L3TrafficIpv4AllRouteEntry 8 }

f3L3TrafficIpv4AllRouteStatus OBJECT-TYPE
    SYNTAX      TrafficIpRouteStatusType
    MAX-ACCESS  read-only
    STATUS      current
    DESCRIPTION
           "It specifies the traffic Ipv4 route status."
    ::= { f3L3TrafficIpv4AllRouteEntry 9 }

f3L3TrafficIpv4AllRouteStorageType OBJECT-TYPE
    SYNTAX      StorageType
    MAX-ACCESS  read-create
    STATUS      current
    DESCRIPTION
           "The type of storage configured for this entry."
    ::= { f3L3TrafficIpv4AllRouteEntry 10 }

f3L3TrafficIpv4AllRouteRowStatus OBJECT-TYPE
    SYNTAX      RowStatus
    MAX-ACCESS  read-create
    STATUS      current
    DESCRIPTION
           "The status of this row.
          	An entry MUST NOT exist in the active state unless all
          	objects in the entry have an appropriate value, as described
          	in the description clause for each writable object.
 	
          	The values of f3L3TrafficIpv4AllRouteRowStatus supported are
          	createAndGo(4) and destroy(6).  All mandatory attributes
          	must be specified in a single SNMP SET request with
          	f3L3TrafficIpv4AllRouteRowStatus value as createAndGo(4).
          	Upon successful row creation, this object has a
          	value of active(1).
 	
          	The f3L3TrafficIpv4AllRouteRowStatus object may be modified if
          	the associated instance of this object is equal to active(1)."
    ::= { f3L3TrafficIpv4AllRouteEntry 11 }

--
--  L3 taffic ipv6 static route Table
--
f3L3TrafficIpv6StaticRouteTable  OBJECT-TYPE
    SYNTAX      SEQUENCE OF F3L3TrafficIpv6StaticRouteEntry
    MAX-ACCESS  not-accessible
    STATUS      current
    DESCRIPTION
            "A list of entries for the L3 Traffic Ipv6 static route."
    ::= { f3L3Objects 46 }

f3L3TrafficIpv6StaticRouteEntry  OBJECT-TYPE
    SYNTAX      F3L3TrafficIpv6StaticRouteEntry
    MAX-ACCESS  not-accessible
    STATUS      current
    DESCRIPTION
            "A conceptual row in the f3L3TrafficIpv6StaticRouteTable."
    INDEX { neIndex, f3VrfIndex, 
            f3L3TrafficIpv6StaticRouteDest, f3L3TrafficIpv6StaticRoutePrefixLength, 
            f3L3TrafficIpv6StaticRouteNextHop, f3L3TrafficIpv6StaticRouteInterface }
    ::= { f3L3TrafficIpv6StaticRouteTable 1 }

F3L3TrafficIpv6StaticRouteEntry ::= SEQUENCE {
    f3L3TrafficIpv6StaticRouteDest                                Ipv6Address,
    f3L3TrafficIpv6StaticRoutePrefixLength                        Integer32,
    f3L3TrafficIpv6StaticRouteNextHop                             DisplayString,
    f3L3TrafficIpv6StaticRouteInterface                           DisplayString,
    f3L3TrafficIpv6StaticRouteMetric                              Integer32,
    f3L3TrafficIpv6StaticRouteStorageType                         StorageType,
    f3L3TrafficIpv6StaticRouteRowStatus                           RowStatus
}

f3L3TrafficIpv6StaticRouteDest OBJECT-TYPE
    SYNTAX      Ipv6Address
    MAX-ACCESS  not-accessible
    STATUS      current
    DESCRIPTION
        "The destination IP address of this route. This object
         may not take a Multicast (Class  D) address value.
         Any assignment (implicit or otherwise) of an instance
         of  this  object to a value x must be rejected if
         the bitwise logical-AND of x with the value of the
         corresponding instance of the static-route-mask
         attribute is not equal to x."
   ::= { f3L3TrafficIpv6StaticRouteEntry 1 }

f3L3TrafficIpv6StaticRoutePrefixLength OBJECT-TYPE
    SYNTAX      Integer32
    MAX-ACCESS  not-accessible
    STATUS      current
    DESCRIPTION
        "Indicate the mask to be logically ANDed with the
         destination  address before being compared to
         the value in the cmStaticRouteDest field. For
         those systems that do not support arbitrary
         subnet masks, an agent constructs the value  of
         the static route mask by reference to the
         IP Address Class. Any assignment (implicit or
         otherwise) of an instance of this object to a
         value x must be rejected if the bitwise logical AND
         of x with the value of the corresponding instance
         of the static-route-dest attribute is not
         equal to static route destination."
   ::= { f3L3TrafficIpv6StaticRouteEntry 2 }

f3L3TrafficIpv6StaticRouteNextHop OBJECT-TYPE
    SYNTAX      DisplayString
    MAX-ACCESS  not-accessible
    STATUS      current
    DESCRIPTION
        "The address of the next router en route."
   ::= { f3L3TrafficIpv6StaticRouteEntry 3 }

f3L3TrafficIpv6StaticRouteInterface OBJECT-TYPE
    SYNTAX      DisplayString (SIZE (0..15))
    MAX-ACCESS  not-accessible
    STATUS      current
    DESCRIPTION
        "Name of the IP interface for the interface
         static route."
   ::= { f3L3TrafficIpv6StaticRouteEntry 4 }

f3L3TrafficIpv6StaticRouteMetric OBJECT-TYPE
    SYNTAX      Integer32
    MAX-ACCESS  read-write
    STATUS      current
    DESCRIPTION
        "The primary routing  metric for this route.
         The semantics of this metric are determined by
         the routing-protocol specified in the route's
         cmStaticRouteProto value. If  this metric is not
         used, its value should be set to 1."
   ::= { f3L3TrafficIpv6StaticRouteEntry 5 }

f3L3TrafficIpv6StaticRouteStorageType OBJECT-TYPE
    SYNTAX      StorageType
    MAX-ACCESS  read-create
    STATUS      current
    DESCRIPTION
        "The storage type for this conceptual row."
   ::= { f3L3TrafficIpv6StaticRouteEntry 6 }

f3L3TrafficIpv6StaticRouteRowStatus OBJECT-TYPE
    SYNTAX      RowStatus
    MAX-ACCESS  read-create
    STATUS      current
    DESCRIPTION
        "The status of this row.  An entry MUST NOT exist in the 
        active state unless all objects in the entry have an 
        appropriate value, as described
        in the description clause for each writable object.

        The values of f3L3TrafficIpv6StaticRouteRowStatus supported are
        createAndGo(4) and destroy(6).  All mandatory attributes
        must be specified in a single SNMP SET request with
        f3L3TrafficIpv6StaticRouteRowStatus value as createAndGo(4).
        Upon successful row creation, this object has a
        value of active(1).

        The f3L3TrafficIpv6StaticRouteRowStatus object may be modified if
        the associated instance of this object is equal to active(1)."
   ::= { f3L3TrafficIpv6StaticRouteEntry 7 }


--
--  L3 taffic ipv6 all route Table
--
f3L3TrafficIpv6AllRouteTable  OBJECT-TYPE
    SYNTAX      SEQUENCE OF F3L3TrafficIpv6AllRouteEntry
    MAX-ACCESS  not-accessible
    STATUS      current
    DESCRIPTION
            "A list of entries for the L3 Traffic Ipv6 route.
             Must set f3VrfActionX as optimizeIpv6RouteRetrieve(7) before get data from this table."
    ::= { f3L3Objects 47 }

f3L3TrafficIpv6AllRouteEntry  OBJECT-TYPE
    SYNTAX      F3L3TrafficIpv6AllRouteEntry
    MAX-ACCESS  not-accessible
    STATUS      current
    DESCRIPTION
            "A conceptual row in the f3L3TrafficIpv6AllRouteTable."
    INDEX { neIndex, f3VrfIndex, 
            f3L3TrafficIpv6AllRouteDest, f3L3TrafficIpv6AllRoutePrefixLength, 
            f3L3TrafficIpv6AllRouteNextHop, f3L3TrafficIpv6AllRouteInterface,
            f3L3TrafficIpv6AllRouteOrigin }
    ::= { f3L3TrafficIpv6AllRouteTable 1 }

F3L3TrafficIpv6AllRouteEntry ::= SEQUENCE {
    f3L3TrafficIpv6AllRouteDest                                Ipv6Address,
    f3L3TrafficIpv6AllRoutePrefixLength                        Integer32,
    f3L3TrafficIpv6AllRouteNextHop                             DisplayString,
    f3L3TrafficIpv6AllRouteInterface                           DisplayString,
    f3L3TrafficIpv6AllRouteOrigin                              TrafficIpRouteOriginType,
    f3L3TrafficIpv6AllRouteMetric                              Integer32,
    f3L3TrafficIpv6AllRouteAdminDistance                       Unsigned32,
    f3L3TrafficIpv6AllRouteStatus                              TrafficIpRouteStatus,
    f3L3TrafficIpv6AllRouteStorageType                         StorageType,
    f3L3TrafficIpv6AllRouteRowStatus                           RowStatus
}

f3L3TrafficIpv6AllRouteDest OBJECT-TYPE
    SYNTAX      Ipv6Address
    MAX-ACCESS  not-accessible
    STATUS      current
    DESCRIPTION
        "The destination IP address of this route. This object
         may not take a Multicast (Class  D) address value.
         Any assignment (implicit or otherwise) of an instance
         of  this  object to a value x must be rejected if
         the bitwise logical-AND of x with the value of the
         corresponding instance of the static-route-mask
         attribute is not equal to x."
   ::= { f3L3TrafficIpv6AllRouteEntry 1 }

f3L3TrafficIpv6AllRoutePrefixLength OBJECT-TYPE
    SYNTAX      Integer32
    MAX-ACCESS  not-accessible
    STATUS      current
    DESCRIPTION
        "Indicate the mask to be logically ANDed with the
         destination  address before being compared to
         the value in the cmStaticRouteDest field. For
         those systems that do not support arbitrary
         subnet masks, an agent constructs the value  of
         the static route mask by reference to the
         IP Address Class. Any assignment (implicit or
         otherwise) of an instance of this object to a
         value x must be rejected if the bitwise logical AND
         of x with the value of the corresponding instance
         of the static-route-dest attribute is not
         equal to static route destination."
   ::= { f3L3TrafficIpv6AllRouteEntry 2 }

f3L3TrafficIpv6AllRouteNextHop OBJECT-TYPE
    SYNTAX      DisplayString
    MAX-ACCESS  not-accessible
    STATUS      current
    DESCRIPTION
        "The address of the next router en route."
   ::= { f3L3TrafficIpv6AllRouteEntry 3 }

f3L3TrafficIpv6AllRouteInterface OBJECT-TYPE
    SYNTAX      DisplayString (SIZE (0..15))
    MAX-ACCESS  not-accessible
    STATUS      current
    DESCRIPTION
        "Name of the IP interface for the interface
         static route."
   ::= { f3L3TrafficIpv6AllRouteEntry 4 }

f3L3TrafficIpv6AllRouteOrigin OBJECT-TYPE
    SYNTAX      TrafficIpRouteOriginType
    MAX-ACCESS  read-only
    STATUS      current
    DESCRIPTION
        "The origin of IP Route."
   ::= { f3L3TrafficIpv6AllRouteEntry 5 }

f3L3TrafficIpv6AllRouteMetric OBJECT-TYPE
    SYNTAX      Integer32
    MAX-ACCESS  read-write
    STATUS      current
    DESCRIPTION
        "The primary routing  metric for this route.
         The semantics of this metric are determined by
         the routing-protocol specified in the route's
         cmStaticRouteProto value. If  this metric is not
         used, its value should be set to 1."
   ::= { f3L3TrafficIpv6AllRouteEntry 6 }

f3L3TrafficIpv6AllRouteAdminDistance OBJECT-TYPE
    SYNTAX      Unsigned32
    MAX-ACCESS  read-only
    STATUS      current
    DESCRIPTION
        "The Administrative Distance of IP Route."
   ::= { f3L3TrafficIpv6AllRouteEntry 7 }

f3L3TrafficIpv6AllRouteStatus OBJECT-TYPE
    SYNTAX      TrafficIpRouteStatus
    MAX-ACCESS  read-only
    STATUS      current
    DESCRIPTION
        "It specifies the traffic Ipv6 route status."
   ::= { f3L3TrafficIpv6AllRouteEntry 8 }

f3L3TrafficIpv6AllRouteStorageType OBJECT-TYPE
    SYNTAX      StorageType
    MAX-ACCESS  read-create
    STATUS      current
    DESCRIPTION
        "The storage type for this conceptual row."
   ::= { f3L3TrafficIpv6AllRouteEntry 9 }

f3L3TrafficIpv6AllRouteRowStatus OBJECT-TYPE
    SYNTAX      RowStatus
    MAX-ACCESS  read-create
    STATUS      current
    DESCRIPTION
        "The status of this row.  An entry MUST NOT exist in the 
        active state unless all objects in the entry have an 
        appropriate value, as described
        in the description clause for each writable object.

        The values of f3L3TrafficIpv6AllRouteRowStatus supported are
        createAndGo(4) and destroy(6).  All mandatory attributes
        must be specified in a single SNMP SET request with
        f3L3TrafficIpv6AllRouteRowStatus value as createAndGo(4).
        Upon successful row creation, this object has a
        value of active(1).

        The f3L3TrafficIpv6AllRouteRowStatus object may be modified if
        the associated instance of this object is equal to active(1)."
   ::= { f3L3TrafficIpv6AllRouteEntry 10 }

--
--  IP Prefix List Table
--

f3IpPrefixListTable  OBJECT-TYPE
    SYNTAX      SEQUENCE OF F3IpPrefixListEntry
    MAX-ACCESS  not-accessible
    STATUS      current
    DESCRIPTION
            "IP Prefix List table."
    ::= { f3L3Objects 48 }

f3IpPrefixListEntry OBJECT-TYPE
    SYNTAX      F3IpPrefixListEntry 
    MAX-ACCESS  not-accessible
    STATUS      current
    DESCRIPTION
            "A conceptual row in the f3IpPrefixListTable. Entries can
            be created/deleted in this table by management application action."
    INDEX { neIndex, 
            f3VrfIndex,
            f3IpPrefixListIndex }
    ::= { f3IpPrefixListTable 1 }

F3IpPrefixListEntry ::= SEQUENCE {
    f3IpPrefixListIndex                  Integer32,
    f3IpPrefixListName                   DisplayString,
    f3IpPrefixListDefaultDisposition     IpPrefixDispositionType,
    f3IpPrefixListStorageType            StorageType,
    f3IpPrefixListRowStatus              RowStatus
}

f3IpPrefixListIndex OBJECT-TYPE
    SYNTAX      Integer32
    MAX-ACCESS  not-accessible
    STATUS      current
    DESCRIPTION
            "An integer index value used to uniquely identify
             this IP Prefix List within a VRF."
    ::= { f3IpPrefixListEntry 1 }

f3IpPrefixListName OBJECT-TYPE
    SYNTAX      DisplayString
    MAX-ACCESS  read-create
    STATUS      current
    DESCRIPTION
            "The name of IP Prefix List."
    ::= { f3IpPrefixListEntry 2 }

f3IpPrefixListDefaultDisposition OBJECT-TYPE
    SYNTAX      IpPrefixDispositionType
    MAX-ACCESS  read-write
    STATUS      current
    DESCRIPTION
            "This indicates the default disposition for the
             prefix that does not match any prefix in the prefix
             list.."
    ::= { f3IpPrefixListEntry 3 }

f3IpPrefixListStorageType OBJECT-TYPE
    SYNTAX      StorageType
    MAX-ACCESS  read-create
    STATUS      current
    DESCRIPTION
        "The storage type for this conceptual row."
   ::= { f3IpPrefixListEntry 4 }

f3IpPrefixListRowStatus OBJECT-TYPE
    SYNTAX      RowStatus
    MAX-ACCESS  read-create
    STATUS      current
    DESCRIPTION
        "The status of this row.  An entry MUST NOT exist in the 
        active state unless all objects in the entry have an 
        appropriate value, as described
        in the description clause for each writable object.

        The values of f3IpPrefixListRowStatus supported are
        createAndGo(4) and destroy(6).  All mandatory attributes
        must be specified in a single SNMP SET request with
        f3IpPrefixListRowStatus value as createAndGo(4).
        Upon successful row creation, this object has a
        value of active(1).

        The f3IpPrefixListRowStatus object may be modified if
        the associated instance of this object is equal to active(1)."
   ::= { f3IpPrefixListEntry 5 }


--
--  IP Prefix Table
--

f3IpPrefixTable  OBJECT-TYPE
    SYNTAX      SEQUENCE OF F3IpPrefixEntry
    MAX-ACCESS  not-accessible
    STATUS      current
    DESCRIPTION
            "IP Prefix table."
    ::= { f3L3Objects 49 }

f3IpPrefixEntry OBJECT-TYPE
    SYNTAX      F3IpPrefixEntry 
    MAX-ACCESS  not-accessible
    STATUS      current
    DESCRIPTION
            "A conceptual row in the f3IpPrefixTable. Entries can
            be created/deleted in this table by management application action."
    INDEX { neIndex, 
            f3VrfIndex,
            f3IpPrefixListIndex,
            f3IpPrefixIndex }
    ::= { f3IpPrefixTable 1 }

F3IpPrefixEntry ::= SEQUENCE {
    f3IpPrefixIndex                    Integer32,
    f3IpPrefix                         DisplayString,
    f3IpPrefixPriority                 Unsigned32,
    f3IpPrefixDisposition              IpPrefixDispositionType,
    f3IpPrefixLessOrEqualPrefixLen     Integer32,
    f3IpPrefixGreaterOrEqualPrefixLen  Integer32,
    f3IpPrefixStorageType              StorageType,
    f3IpPrefixRowStatus                RowStatus
}

f3IpPrefixIndex OBJECT-TYPE
    SYNTAX      Integer32
    MAX-ACCESS  not-accessible
    STATUS      current
    DESCRIPTION
            "An integer index value used to uniquely identify
             this IP Prefix entry within a IP Prefix List."
    ::= { f3IpPrefixEntry 1 }
    
f3IpPrefix OBJECT-TYPE
    SYNTAX      DisplayString
    MAX-ACCESS  read-create
    STATUS      current
    DESCRIPTION
            "The IP Prefix.  The length is up to 64 characters."
    ::= { f3IpPrefixEntry 2 }

f3IpPrefixPriority OBJECT-TYPE
    SYNTAX      Unsigned32
    MAX-ACCESS  read-write
    STATUS      current
    DESCRIPTION
            "This dictates the order in which this entry is applied 
             relative to the IP Prefix List. These values need not 
             be sequential and can have gaps. The priority of 
             the IP Prefix Entry within a list shall be unique. 
             Higher the value lower the priority."
    ::= { f3IpPrefixEntry 3 }

f3IpPrefixDisposition OBJECT-TYPE
    SYNTAX      IpPrefixDispositionType
    MAX-ACCESS  read-write
    STATUS      current
    DESCRIPTION
            "This indicates whether to permit or deny the prefix."
    ::= { f3IpPrefixEntry 4 }

f3IpPrefixLessOrEqualPrefixLen OBJECT-TYPE
    SYNTAX      Integer32
    MAX-ACCESS  read-write
    STATUS      current
    DESCRIPTION
            "This allows specifying a prefix length which allows 
            filtering networks with more specific prefixes within
             this Prefix attribute. For example, if this value 
             is 16 and the Prefix attribute is <10.0.0.0/8>, 
             then all the networks in 10.0.0.0/8 that have prefix 
             that is 16 or less will be filtered. A specific value 
             of Prefix 0.0.0.0/0 with a value of 32 for this attribute 
             implies all the networks and it could be used for the 
             rule with highest priority value (lowest priority) 
             that permits all networks that have not been filtered 
             by higher priority entries."
    ::= { f3IpPrefixEntry 5 }

f3IpPrefixGreaterOrEqualPrefixLen OBJECT-TYPE
    SYNTAX      Integer32
    MAX-ACCESS  read-write
    STATUS      current
    DESCRIPTION
            "This allows specifying a prefix length which allows 
            filtering all networks in the specified Prefix that 
            are at least the length specified for this attribute. 
            This attribute value shall be greater than the Prefix 
            Length of the Prefix attribute. For example, if this 
            value is 16 and the Prefix attribute is <10.0.0.0/8>, 
            then all the networks in 10.0.0.0/8 with a prefix 
            greater than or equal to 16 are filtered."
    ::= { f3IpPrefixEntry 6 }

f3IpPrefixStorageType OBJECT-TYPE
    SYNTAX      StorageType
    MAX-ACCESS  read-create
    STATUS      current
    DESCRIPTION
        "The storage type for this conceptual row."
   ::= { f3IpPrefixEntry 7 }

f3IpPrefixRowStatus OBJECT-TYPE
    SYNTAX      RowStatus
    MAX-ACCESS  read-create
    STATUS      current
    DESCRIPTION
        "The status of this row.  An entry MUST NOT exist in the 
        active state unless all objects in the entry have an 
        appropriate value, as described
        in the description clause for each writable object.

        The values of f3IpPrefixRowStatus supported are
        createAndGo(4) and destroy(6).  All mandatory attributes
        must be specified in a single SNMP SET request with
        f3IpPrefixRowStatus value as createAndGo(4).
        Upon successful row creation, this object has a
        value of active(1).

        The f3IpPrefixRowStatus object may be modified if
        the associated instance of this object is equal to active(1)."
   ::= { f3IpPrefixEntry 8 }


--
-- L3 Traffic IP Interface RAP Prefix Table
--

f3L3TrafficIPInterfaceRAPrefixTable OBJECT-TYPE
    SYNTAX      SEQUENCE OF F3L3TrafficIPInterfaceRAPrefixEntry
    MAX-ACCESS  not-accessible
    STATUS      current
    DESCRIPTION
        "Traffic IP interface RAP prefix table."

   ::= { f3L3Objects 50 }

f3L3TrafficIPInterfaceRAPrefixEntry OBJECT-TYPE
    SYNTAX      F3L3TrafficIPInterfaceRAPrefixEntry
    MAX-ACCESS  not-accessible
    STATUS      current
    DESCRIPTION
        "A conceptual row in f3L3TrafficIPInterfaceRAPrefixTable."
    INDEX { neIndex, shelfIndex, slotIndex,
            f3L3FlowPointPortIndex, f3L3FlowPointIndex, 
            f3L3TrafficIPIfIndex, f3L3TrafficIPInterfaceRAPrefixIndex }

   ::= { f3L3TrafficIPInterfaceRAPrefixTable 1 }

F3L3TrafficIPInterfaceRAPrefixEntry ::= SEQUENCE {
    f3L3TrafficIPInterfaceRAPrefixIndex                  Integer32,
    f3L3TrafficIPInterfaceRAPrefixAdvertiseEnabled       TruthValue,
    f3L3TrafficIPInterfaceRAPrefix                       Ipv6Address,
    f3L3TrafficIPInterfaceRAPrefixLength                 Integer32,
    f3L3TrafficIPInterfaceRAPrefixValidLifeTime          Unsigned32,
    f3L3TrafficIPInterfaceRAPrefixPreferredLifeTime      Unsigned32,
    f3L3TrafficIPInterfaceRAPrefixStorageType            StorageType,
    f3L3TrafficIPInterfaceRAPrefixRowStatus              RowStatus
}

f3L3TrafficIPInterfaceRAPrefixIndex OBJECT-TYPE
    SYNTAX      Integer32
    MAX-ACCESS  not-accessible
    STATUS      current
    DESCRIPTION
           "The unique integer index value corresponding to a traffic IP interface RA prefix."
    ::= { f3L3TrafficIPInterfaceRAPrefixEntry 1 }

f3L3TrafficIPInterfaceRAPrefixAdvertiseEnabled OBJECT-TYPE
    SYNTAX      TruthValue
    MAX-ACCESS  read-write
    STATUS      current
    DESCRIPTION
           "This attribute is to enable to Advertise prefix to link in router mode."
    ::= { f3L3TrafficIPInterfaceRAPrefixEntry 2 }

f3L3TrafficIPInterfaceRAPrefix OBJECT-TYPE
    SYNTAX      Ipv6Address
    MAX-ACCESS  read-write
    STATUS      current
    DESCRIPTION
           "This is the IPv6 Prefix to be dispatched to the link in Router mode."
    ::= { f3L3TrafficIPInterfaceRAPrefixEntry 3 }

f3L3TrafficIPInterfaceRAPrefixLength OBJECT-TYPE
    SYNTAX      Integer32
    MAX-ACCESS  read-write
    STATUS      current
    DESCRIPTION
           "Prefix length."
    ::= { f3L3TrafficIPInterfaceRAPrefixEntry 4 }

f3L3TrafficIPInterfaceRAPrefixValidLifeTime OBJECT-TYPE
    SYNTAX      Unsigned32
    MAX-ACCESS  read-write
    STATUS      current
    DESCRIPTION
           "This attribute is used to specify fixed Valid lifetime of distributed prefix in seconds
            All ones may be set for unlimited lifetime."
    ::= { f3L3TrafficIPInterfaceRAPrefixEntry 5 }

f3L3TrafficIPInterfaceRAPrefixPreferredLifeTime OBJECT-TYPE
    SYNTAX      Unsigned32
    MAX-ACCESS  read-write
    STATUS      current
    DESCRIPTION
           "This attribute is used to specify fixed time interval for unrestricted use of prefix.
            When this time has been expired the address is considered as deprecated as specified
            in RFC4862 Preferred lifetime shall not be greater than the Valid Lifetime. All
            ones may be set for unlimited lifetime."
    ::= { f3L3TrafficIPInterfaceRAPrefixEntry 6 }

f3L3TrafficIPInterfaceRAPrefixStorageType OBJECT-TYPE
    SYNTAX      StorageType
    MAX-ACCESS  read-create
    STATUS      current
    DESCRIPTION
        "The storage type for this conceptual row."
   ::= { f3L3TrafficIPInterfaceRAPrefixEntry 7 }

f3L3TrafficIPInterfaceRAPrefixRowStatus OBJECT-TYPE
    SYNTAX      RowStatus
    MAX-ACCESS  read-create
    STATUS      current
    DESCRIPTION
        "The status of this row.  An entry MUST NOT exist in the 
        active state unless all objects in the entry have an 
        appropriate value, as described
        in the description clause for each writable object.

        The values of f3L3TrafficIPInterfaceRAPrefixRowStatus supported are
        createAndGo(4) and destroy(6).  All mandatory attributes
        must be specified in a single SNMP SET request with
        f3L3TrafficIPInterfaceRAPrefixRowStatus value as createAndGo(4).
        Upon successful row creation, this object has a
        value of active(1).

        The f3L3TrafficIPInterfaceRAPrefixRowStatus object may be modified if
        the associated instance of this object is equal to active(1)."
   ::= { f3L3TrafficIPInterfaceRAPrefixEntry 8 }


--
-- L3 traffic IP interface Ndp Table
--

f3L3TrafficIPInterfaceNdpTable OBJECT-TYPE
    SYNTAX      SEQUENCE OF F3L3TrafficIPInterfaceNdpEntry
    MAX-ACCESS  not-accessible
    STATUS      current
    DESCRIPTION
        "Traffic IPv6 NDP table.
         Must set f3L3TrafficIPIfActionX as optimizeNdpRetrieve(2) before get data from this table."

   ::= { f3L3Objects 51 }

f3L3TrafficIPInterfaceNdpEntry OBJECT-TYPE
    SYNTAX      F3L3TrafficIPInterfaceNdpEntry
    MAX-ACCESS  not-accessible
    STATUS      current
    DESCRIPTION
        "A conceptual row in f3L3TrafficIPInterfaceNdpTable."
    INDEX { neIndex, shelfIndex, slotIndex,
            f3L3FlowPointPortIndex, f3L3FlowPointIndex, 
            f3L3TrafficIPv6IfIndex, f3L3TrafficIPv6NdpIPv6Addr }

   ::= { f3L3TrafficIPInterfaceNdpTable 1 }

F3L3TrafficIPInterfaceNdpEntry ::= SEQUENCE {
    f3L3TrafficIPInterfaceNdpIPv6Addr              Ipv6Address,
    f3L3TrafficIPInterfaceNdpInterface             DisplayString,
    f3L3TrafficIPInterfaceNdpMacAddress            MacAddress,
    f3L3TrafficIPInterfaceNdpType                  IpEntryType,
    f3L3TrafficIPInterfaceNdpReachabilityState     NdpNeighborReachabilityState,
    f3L3TrafficIPInterfaceNdpAge                   Integer32,
    f3L3TrafficIPInterfaceNdpStorageType           StorageType,
    f3L3TrafficIPInterfaceNdpRowStatus             RowStatus
}

f3L3TrafficIPInterfaceNdpIPv6Addr OBJECT-TYPE
    SYNTAX      Ipv6Address
    MAX-ACCESS  not-accessible
    STATUS      current
    DESCRIPTION
        "This is the IP address of the NDP Entry."
    ::= { f3L3TrafficIPInterfaceNdpEntry 1 }

f3L3TrafficIPInterfaceNdpInterface OBJECT-TYPE
    SYNTAX      DisplayString (SIZE (0..15))
    MAX-ACCESS  read-create
    STATUS      current
    DESCRIPTION
        "This is the IP interface for the NDP Entry."
    ::= { f3L3TrafficIPInterfaceNdpEntry 2 }

f3L3TrafficIPInterfaceNdpMacAddress OBJECT-TYPE
    SYNTAX      MacAddress
    MAX-ACCESS  read-create
    STATUS      current
    DESCRIPTION
        "This is the MAC address of the NDP Entry."
    ::= { f3L3TrafficIPInterfaceNdpEntry 3 }

f3L3TrafficIPInterfaceNdpType OBJECT-TYPE
    SYNTAX      IpEntryType
    MAX-ACCESS  read-create
    STATUS      current
    DESCRIPTION
        "The type of NDP Entry.
         Note that static entries can be created."
    ::= { f3L3TrafficIPInterfaceNdpEntry 4 }

f3L3TrafficIPInterfaceNdpReachabilityState OBJECT-TYPE
    SYNTAX      NdpNeighborReachabilityState
    MAX-ACCESS  read-only
    STATUS      current
    DESCRIPTION
        "This is the reachability state of the NDP Entry."
    ::= { f3L3TrafficIPInterfaceNdpEntry 5 }

f3L3TrafficIPInterfaceNdpAge OBJECT-TYPE
    SYNTAX      Integer32
    MAX-ACCESS  read-only
    STATUS      current
    DESCRIPTION
        "Indicates entry age in seconds."
    ::= { f3L3TrafficIPInterfaceNdpEntry 6 }

f3L3TrafficIPInterfaceNdpStorageType OBJECT-TYPE
    SYNTAX      StorageType
    MAX-ACCESS  read-create
    STATUS      current
    DESCRIPTION
        "The storage type for this conceptual row."
   ::= { f3L3TrafficIPInterfaceNdpEntry 7 }

f3L3TrafficIPInterfaceNdpRowStatus OBJECT-TYPE
    SYNTAX      RowStatus
    MAX-ACCESS  read-create
    STATUS      current
    DESCRIPTION
        "The status of this row.  An entry MUST NOT exist in the 
        active state unless all objects in the entry have an 
        appropriate value, as described
        in the description clause for each writable object.

        The values of f3L3TrafficIPInterfaceNdpRowStatus supported are
        createAndGo(4) and destroy(6).  All mandatory attributes
        must be specified in a single SNMP SET request with
        f3L3TrafficIPInterfaceNdpRowStatus value as createAndGo(4).
        Upon successful row creation, this object has a
        value of active(1).

        The f3L3TrafficIPInterfaceNdpRowStatus object may be modified if
        the associated instance of this object is equal to active(1)."
   ::= { f3L3TrafficIPInterfaceNdpEntry 8 }


--
--  L3 traffic IP interface IPv6 Address Table
--

f3L3TrafficIPInterfaceIPv6AddressTable  OBJECT-TYPE
    SYNTAX      SEQUENCE OF F3L3TrafficIPInterfaceIPv6AddressEntry
    MAX-ACCESS  not-accessible
    STATUS      current
    DESCRIPTION
            "Traffic interface IPv6 address table.
             Must set f3L3TrafficIPIfActionX as optimizeIPv6AddressEntryRetrieve(3) before get data from this table."
    ::= { f3L3Objects 52 }

f3L3TrafficIPInterfaceIPv6AddressEntry  OBJECT-TYPE
    SYNTAX      F3L3TrafficIPInterfaceIPv6AddressEntry
    MAX-ACCESS  not-accessible
    STATUS      current
    DESCRIPTION
            "A conceptual row in the f3L3TrafficIPInterfaceIPv6AddressTable."
    INDEX { neIndex, shelfIndex, slotIndex,
            f3L3FlowPointPortIndex, f3L3FlowPointIndex, 
            f3L3TrafficIPIfIndex, f3L3TrafficIPInterfaceIPv6AddressIndex }
    ::= { f3L3TrafficIPInterfaceIPv6AddressTable 1 }

F3L3TrafficIPInterfaceIPv6AddressEntry ::= SEQUENCE {
    f3L3TrafficIPInterfaceIPv6AddressIndex                               Integer32,
    f3L3TrafficIPInterfaceIPv6AddressAssignMode                          Ipv6AddressAssignMode,
    f3L3TrafficIPInterfaceIPv6AddressUnicastAddr                         Ipv6Address,
    f3L3TrafficIPInterfaceIPv6AddressUnicastAddrPrefixLength             Integer32,
    f3L3TrafficIPInterfaceIPv6AddressUnicastAddrAutoGenPrefix            DisplayString,
    f3L3TrafficIPInterfaceIPv6AddressStorageType                         StorageType,
    f3L3TrafficIPInterfaceIPv6AddressRowStatus                           RowStatus
}

f3L3TrafficIPInterfaceIPv6AddressIndex OBJECT-TYPE
    SYNTAX      Integer32
    MAX-ACCESS  not-accessible
    STATUS      current
    DESCRIPTION
           "The unique integer index value corresponding to a traffic IP interface IPv6 unicast address."
    ::= { f3L3TrafficIPInterfaceIPv6AddressEntry 1 }

f3L3TrafficIPInterfaceIPv6AddressAssignMode OBJECT-TYPE
    SYNTAX      Ipv6AddressAssignMode
    MAX-ACCESS  read-write
    STATUS      current
    DESCRIPTION
           "The assignment mode of IPv6 Unicast Address."
    ::= { f3L3TrafficIPInterfaceIPv6AddressEntry 2 }

f3L3TrafficIPInterfaceIPv6AddressUnicastAddr OBJECT-TYPE
    SYNTAX      Ipv6Address
    MAX-ACCESS  read-write
    STATUS      current
    DESCRIPTION
           "This is IPv6 Unicast Address."
    ::= { f3L3TrafficIPInterfaceIPv6AddressEntry 3 }

f3L3TrafficIPInterfaceIPv6AddressUnicastAddrPrefixLength OBJECT-TYPE
    SYNTAX      Integer32
    MAX-ACCESS  read-write
    STATUS      current
    DESCRIPTION
           "This is prefix length of the unicast address."
    ::= { f3L3TrafficIPInterfaceIPv6AddressEntry 4 }

f3L3TrafficIPInterfaceIPv6AddressUnicastAddrAutoGenPrefix OBJECT-TYPE
    SYNTAX      DisplayString
    MAX-ACCESS  read-write
    STATUS      current
    DESCRIPTION
           "This is prefix of the unicast address in automatic address assignment mode."
    ::= { f3L3TrafficIPInterfaceIPv6AddressEntry 5 }

f3L3TrafficIPInterfaceIPv6AddressStorageType OBJECT-TYPE
    SYNTAX      StorageType
    MAX-ACCESS  read-create
    STATUS      current
    DESCRIPTION
        "The storage type for this conceptual row."
   ::= { f3L3TrafficIPInterfaceIPv6AddressEntry 6 }

f3L3TrafficIPInterfaceIPv6AddressRowStatus OBJECT-TYPE
    SYNTAX      RowStatus
    MAX-ACCESS  read-create
    STATUS      current
    DESCRIPTION
        "The status of this row.  An entry MUST NOT exist in the 
        active state unless all objects in the entry have an 
        appropriate value, as described
        in the description clause for each writable object.

        The values of f3L3TrafficIPInterfaceIPv6AddressRowStatus supported are
        createAndGo(4) and destroy(6).  All mandatory attributes
        must be specified in a single SNMP SET request with
        f3L3TrafficIPInterfaceIPv6AddressRowStatus value as createAndGo(4).
        Upon successful row creation, this object has a
        value of active(1).

        The f3L3TrafficIPInterfaceIPv6AddressRowStatus object may be modified if
        the associated instance of this object is equal to active(1)."
   ::= { f3L3TrafficIPInterfaceIPv6AddressEntry 7 }


--
--  Traffic Ospf Area Route Summary Table
-- 
f3L3TrafficOspfAreaRouteSummaryTable  OBJECT-TYPE
    SYNTAX      SEQUENCE OF F3L3TrafficOspfAreaRouteSummaryEntry
    MAX-ACCESS  not-accessible
    STATUS      current
    DESCRIPTION
            "A list of entries for the Traffic OSPF Interface."
    ::= { f3L3Objects 53 }

f3L3TrafficOspfAreaRouteSummaryEntry  OBJECT-TYPE
    SYNTAX      F3L3TrafficOspfAreaRouteSummaryEntry
    MAX-ACCESS  not-accessible
    STATUS      current
    DESCRIPTION
            "A conceptual row in the f3L3TrafficOspfAreaRouteSummaryTable."
    INDEX { neIndex,
            f3VrfIndex,
            f3VrfOspfRouterIndex,
            f3L3TrafficOspfAreaIndex,
            f3L3TrafficOspfAreaRouteSummaryPrefix }
    ::= { f3L3TrafficOspfAreaRouteSummaryTable 1 }

F3L3TrafficOspfAreaRouteSummaryEntry ::= SEQUENCE {
    f3L3TrafficOspfAreaRouteSummaryPrefix                       DisplayString,
    f3L3TrafficOspfAreaRouteSummaryCost                         Unsigned32,
    f3L3TrafficOspfAreaRouteSummaryAdvertise                    TruthValue,
    f3L3TrafficOspfAreaRouteSummaryStorageType                  StorageType,
    f3L3TrafficOspfAreaRouteSummaryRowStatus                    RowStatus
}

f3L3TrafficOspfAreaRouteSummaryPrefix OBJECT-TYPE
    SYNTAX      DisplayString
    MAX-ACCESS  not-accessible
    STATUS      current
    DESCRIPTION
           "The prefix of the Traffic OSPF Area Route Summary entry."
    ::= { f3L3TrafficOspfAreaRouteSummaryEntry 1 }

f3L3TrafficOspfAreaRouteSummaryCost OBJECT-TYPE
    SYNTAX      Unsigned32
    MAX-ACCESS  read-create
    STATUS      current
    DESCRIPTION
            "The cost of the Traffic OSPF Area Route Summary."
    ::= { f3L3TrafficOspfAreaRouteSummaryEntry 2 }


f3L3TrafficOspfAreaRouteSummaryAdvertise OBJECT-TYPE
    SYNTAX      TruthValue
    MAX-ACCESS  read-create
    STATUS      current
    DESCRIPTION
            "Enable/Disable advertise Traffic OSPF Area Route Summary."
    ::= { f3L3TrafficOspfAreaRouteSummaryEntry 3 }

f3L3TrafficOspfAreaRouteSummaryStorageType OBJECT-TYPE
    SYNTAX      StorageType
    MAX-ACCESS  read-create
    STATUS      current
    DESCRIPTION
           "The type of storage configured for this entry."
    ::= { f3L3TrafficOspfAreaRouteSummaryEntry 4 }

f3L3TrafficOspfAreaRouteSummaryRowStatus OBJECT-TYPE
    SYNTAX      RowStatus
    MAX-ACCESS  read-create
    STATUS      current
    DESCRIPTION
           "The status of this row.
                An entry MUST NOT exist in the active state unless all
                objects in the entry have an appropriate value, as described
                in the description clause for each writable object.

                The values of f3L3TrafficOspfAreaRouteSummaryRowStatus supported are
                createAndGo(4) and destroy(6).  All mandatory attributes
                must be specified in a single SNMP SET request with
                f3L3TrafficOspfAreaRouteSummaryRowStatus value as createAndGo(4).
                Upon successful row creation, this object has a
                value of active(1).

                The f3L3TrafficOspfAreaRouteSummaryRowStatus object may be modified if
                the associated instance of this object is equal to active(1)."
    ::= { f3L3TrafficOspfAreaRouteSummaryEntry 5 }

--
-- L3 flow point Current Statistics Table
--
f3L3FlowPointStatsTable OBJECT-TYPE
    SYNTAX      SEQUENCE OF F3L3FlowPointStatsEntry
    MAX-ACCESS  not-accessible
    STATUS      current
    DESCRIPTION
            "A collection of L3 Flow Point related statistics.  
             These reflect the current data."
    ::= { f3L3Performance 1 }

f3L3FlowPointStatsEntry OBJECT-TYPE
    SYNTAX      F3L3FlowPointStatsEntry 
    MAX-ACCESS  not-accessible
    STATUS      current
    DESCRIPTION
            "A conceptual row in the f3L3FlowPointStatsTable.
             Entries exist in this table for each L3 flow point."
    INDEX { neIndex, shelfIndex, slotIndex, f3L3FlowPointPortTypeIndex, 
            f3L3FlowPointPortIndex, f3L3FlowPointIndex, f3L3FlowPointStatsIndex }
    ::= { f3L3FlowPointStatsTable 1 }

F3L3FlowPointStatsEntry ::= SEQUENCE {
    f3L3FlowPointStatsIndex               Integer32,
    f3L3FlowPointStatsIntervalType        CmPmIntervalType,
    f3L3FlowPointStatsValid               TruthValue,
    f3L3FlowPointStatsAction              CmPmBinAction,
    f3L3FlowPointStatsFMG                 PerfCounter64,
    f3L3FlowPointStatsFMY                 PerfCounter64,
    f3L3FlowPointStatsFMRD                PerfCounter64,
    f3L3FlowPointStatsFTD                 PerfCounter64,
    f3L3FlowPointStatsFragmentedDropAcl   PerfCounter64,
    f3L3FlowPointStatsAclRuleDrop         PerfCounter64,
    f3L3FlowPointStatsTtlEqual1Drop       PerfCounter64,
    f3L3FlowPointStatsFrameTx             PerfCounter64,
    f3L3FlowPointStatsFrameRx             PerfCounter64,
    f3L3FlowPointStatsNoRouteDrop         PerfCounter64,
    f3L3FlowPointStatsHopLimitDrop        PerfCounter64
}

f3L3FlowPointStatsIndex OBJECT-TYPE
    SYNTAX      Integer32 (1..4)
    MAX-ACCESS  read-only
    STATUS      current
    DESCRIPTION
            "An arbitrary integer index value used to uniquely identify
            this L3 flow point statistics entry. 
            1 - 15min
            2 - 1day
            3 - rollover
            4 - 5min"
    ::= { f3L3FlowPointStatsEntry 1 }

f3L3FlowPointStatsIntervalType OBJECT-TYPE
    SYNTAX      CmPmIntervalType
    MAX-ACCESS  read-only
    STATUS      current
    DESCRIPTION
            "Interval over which Performance Monitoring data is collected."
    ::= { f3L3FlowPointStatsEntry 2 }

f3L3FlowPointStatsValid OBJECT-TYPE
    SYNTAX      TruthValue
    MAX-ACCESS  read-only
    STATUS      current
    DESCRIPTION
            "Indicates the validity of the bin."
    ::= { f3L3FlowPointStatsEntry 3 }

f3L3FlowPointStatsAction OBJECT-TYPE
    SYNTAX      CmPmBinAction
    MAX-ACCESS  read-write
    STATUS      current
    DESCRIPTION
            "Allows the Manager to clear the bin."
    ::= { f3L3FlowPointStatsEntry 4 }

f3L3FlowPointStatsFMG OBJECT-TYPE
     SYNTAX     PerfCounter64
     MAX-ACCESS read-only
     STATUS     current
     DESCRIPTION
         "The number of Frames Marked Green."
     ::= { f3L3FlowPointStatsEntry 5 }

f3L3FlowPointStatsFMY OBJECT-TYPE
     SYNTAX     PerfCounter64
     MAX-ACCESS read-only
     STATUS     current
     DESCRIPTION
         "The number of Frames Marked Yellow."
     ::= { f3L3FlowPointStatsEntry 6 }

f3L3FlowPointStatsFMRD OBJECT-TYPE
     SYNTAX     PerfCounter64
     MAX-ACCESS read-only
     STATUS     current
     DESCRIPTION
         "The number of Frames Marked Red and Discarded."
     ::= { f3L3FlowPointStatsEntry 7 }

f3L3FlowPointStatsFTD OBJECT-TYPE
     SYNTAX     PerfCounter64
     MAX-ACCESS read-only
     STATUS     current
     DESCRIPTION
         "The number of Frames Tail Dropped."
     ::= { f3L3FlowPointStatsEntry 8 }

f3L3FlowPointStatsFragmentedDropAcl OBJECT-TYPE
     SYNTAX     PerfCounter64
     MAX-ACCESS read-only
     STATUS     current
     DESCRIPTION
         "The number of dropped fragmented packets."
     ::= { f3L3FlowPointStatsEntry 9 }

f3L3FlowPointStatsAclRuleDrop OBJECT-TYPE
     SYNTAX     PerfCounter64
     MAX-ACCESS read-only
     STATUS     current
     DESCRIPTION
         "The number of dropped packets due to ACL rule."
     ::= { f3L3FlowPointStatsEntry 10 }

f3L3FlowPointStatsTtlEqual1Drop OBJECT-TYPE
     SYNTAX     PerfCounter64
     MAX-ACCESS read-only
     STATUS     current
     DESCRIPTION
         " the number of dropped packets due to ttl's value is 1."
     ::= { f3L3FlowPointStatsEntry 11 }

f3L3FlowPointStatsFrameTx OBJECT-TYPE
     SYNTAX     PerfCounter64
     MAX-ACCESS read-only
     STATUS     current
     DESCRIPTION
         "The number of total transmitted frames."
     ::= { f3L3FlowPointStatsEntry 12 }

f3L3FlowPointStatsFrameRx OBJECT-TYPE
     SYNTAX     PerfCounter64
     MAX-ACCESS read-only
     STATUS     current
     DESCRIPTION
         " The number of total received frames."
     ::= { f3L3FlowPointStatsEntry 13 }

f3L3FlowPointStatsNoRouteDrop OBJECT-TYPE
     SYNTAX     PerfCounter64
     MAX-ACCESS read-only
     STATUS     current
     DESCRIPTION
         " The number of frames drop due to no route."
     ::= { f3L3FlowPointStatsEntry 14 }

f3L3FlowPointStatsHopLimitDrop OBJECT-TYPE
     SYNTAX     PerfCounter64
     MAX-ACCESS read-only
     STATUS     current
     DESCRIPTION
         " The number of frames drop due to hop limit."
     ::= { f3L3FlowPointStatsEntry 15 }


--
-- L3 flow point history Statistics Table
--
f3L3FlowPointHistoryTable OBJECT-TYPE
    SYNTAX      SEQUENCE OF F3L3FlowPointHistoryEntry
    MAX-ACCESS  not-accessible
    STATUS      current
    DESCRIPTION
            "A collection of L3 Flow Point related statistics.  
             These reflect the current data."
    ::= { f3L3Performance 2 }

f3L3FlowPointHistoryEntry OBJECT-TYPE
    SYNTAX      F3L3FlowPointHistoryEntry 
    MAX-ACCESS  not-accessible
    STATUS      current
    DESCRIPTION
            "A conceptual row in the f3L3FlowPointHistoryTable.
             Entries exist in this table for each L3 flow point."
    INDEX { neIndex, shelfIndex, slotIndex, f3L3FlowPointPortTypeIndex, 
            f3L3FlowPointPortIndex, f3L3FlowPointIndex, f3L3FlowPointStatsIndex, f3L3FlowPointHistoryIndex }
    ::= { f3L3FlowPointHistoryTable 1 }

F3L3FlowPointHistoryEntry ::= SEQUENCE {
    f3L3FlowPointHistoryIndex               Integer32,
    f3L3FlowPointHistoryTime                DateAndTime,
    f3L3FlowPointHistoryValid               TruthValue,
    f3L3FlowPointHistoryAction              CmPmBinAction,
    f3L3FlowPointHistoryFMG                 PerfCounter64,
    f3L3FlowPointHistoryFMY                 PerfCounter64,
    f3L3FlowPointHistoryFMRD                PerfCounter64,
    f3L3FlowPointHistoryFTD                 PerfCounter64,
    f3L3FlowPointHistoryFragmentedDropAcl   PerfCounter64,
    f3L3FlowPointHistoryAclRuleDrop         PerfCounter64,
    f3L3FlowPointHistoryTtlEqual1Drop       PerfCounter64,
    f3L3FlowPointHistoryFrameTx             PerfCounter64,
    f3L3FlowPointHistoryFrameRx             PerfCounter64,
    f3L3FlowPointHistoryNoRouteDrop         PerfCounter64,
    f3L3FlowPointHistoryHopLimitDrop        PerfCounter64
}

f3L3FlowPointHistoryIndex OBJECT-TYPE
    SYNTAX      Integer32 (1..65535)
    MAX-ACCESS  read-only
    STATUS      current
    DESCRIPTION
            "An arbitrary integer index value used to uniquely identify
            this L3 flow point statistics entry. 
            1 - 15min
            2 - 1day
            3 - rollover
            4 - 5min"
    ::= { f3L3FlowPointHistoryEntry 1 }

f3L3FlowPointHistoryTime OBJECT-TYPE
    SYNTAX      DateAndTime
    MAX-ACCESS  read-only
    STATUS      current
    DESCRIPTION
            "Indicates the time of history bin creation." 
    ::= { f3L3FlowPointHistoryEntry 2 }

f3L3FlowPointHistoryValid OBJECT-TYPE
    SYNTAX      TruthValue
    MAX-ACCESS  read-only
    STATUS      current
    DESCRIPTION
            "Indicates the validity of the bin."
    ::= { f3L3FlowPointHistoryEntry 3 }

f3L3FlowPointHistoryAction OBJECT-TYPE
    SYNTAX      CmPmBinAction
    MAX-ACCESS  read-write
    STATUS      current
    DESCRIPTION
            "Allows the Manager to clear the bin."
    ::= { f3L3FlowPointHistoryEntry 4 }

f3L3FlowPointHistoryFMG OBJECT-TYPE
     SYNTAX     PerfCounter64
     MAX-ACCESS read-only
     STATUS     current
     DESCRIPTION
         "The number of Frames Marked Green."
     ::= { f3L3FlowPointHistoryEntry 5 }

f3L3FlowPointHistoryFMY OBJECT-TYPE
     SYNTAX     PerfCounter64
     MAX-ACCESS read-only
     STATUS     current
     DESCRIPTION
         "The number of Frames Marked Yellow."
     ::= { f3L3FlowPointHistoryEntry 6 }

f3L3FlowPointHistoryFMRD OBJECT-TYPE
     SYNTAX     PerfCounter64
     MAX-ACCESS read-only
     STATUS     current
     DESCRIPTION
         "The number of Frames Marked Red and Discarded."
     ::= { f3L3FlowPointHistoryEntry 7 }

f3L3FlowPointHistoryFTD OBJECT-TYPE
     SYNTAX     PerfCounter64
     MAX-ACCESS read-only
     STATUS     current
     DESCRIPTION
         "The number of Frames Tail Dropped."
     ::= { f3L3FlowPointHistoryEntry 8 }

f3L3FlowPointHistoryFragmentedDropAcl OBJECT-TYPE
     SYNTAX     PerfCounter64
     MAX-ACCESS read-only
     STATUS     current
     DESCRIPTION
         "The number of dropped fragmented packets."
     ::= { f3L3FlowPointHistoryEntry 9 }

f3L3FlowPointHistoryAclRuleDrop OBJECT-TYPE
     SYNTAX     PerfCounter64
     MAX-ACCESS read-only
     STATUS     current
     DESCRIPTION
         "The number of dropped packets due to ACL rule."
     ::= { f3L3FlowPointHistoryEntry 10 }

f3L3FlowPointHistoryTtlEqual1Drop OBJECT-TYPE
     SYNTAX     PerfCounter64
     MAX-ACCESS read-only
     STATUS     current
     DESCRIPTION
         " the number of dropped packets due to ttl's value is 1."
     ::= { f3L3FlowPointHistoryEntry 11 }

f3L3FlowPointHistoryFrameTx OBJECT-TYPE
     SYNTAX     PerfCounter64
     MAX-ACCESS read-only
     STATUS     current
     DESCRIPTION
         "The number of total transmitted frames."
     ::= { f3L3FlowPointHistoryEntry 12 }

f3L3FlowPointHistoryFrameRx OBJECT-TYPE
     SYNTAX     PerfCounter64
     MAX-ACCESS read-only
     STATUS     current
     DESCRIPTION
         " the number of total recieved frames."
     ::= { f3L3FlowPointHistoryEntry 13 }

f3L3FlowPointHistoryNoRouteDrop OBJECT-TYPE
     SYNTAX     PerfCounter64
     MAX-ACCESS read-only
     STATUS     current
     DESCRIPTION
         " the number of frames dropped due to no route."
     ::= { f3L3FlowPointHistoryEntry 14 }

f3L3FlowPointHistoryHopLimitDrop OBJECT-TYPE
     SYNTAX     PerfCounter64
     MAX-ACCESS read-only
     STATUS     current
     DESCRIPTION
         " the number of frames dropped due to hop limit."
     ::= { f3L3FlowPointHistoryEntry 15 }


--
-- L3 Flow Point Threshold Table
--
f3L3FlowPointThresholdTable OBJECT-TYPE
    SYNTAX      SEQUENCE OF F3L3FlowPointThresholdEntry
    MAX-ACCESS  not-accessible
    STATUS      current
    DESCRIPTION
            "A table of entries that allow manageability of L3 Flow Point Thresholds."
    ::= { f3L3Performance 3 }

f3L3FlowPointThresholdEntry OBJECT-TYPE
    SYNTAX      F3L3FlowPointThresholdEntry
    MAX-ACCESS  not-accessible
    STATUS      current
    DESCRIPTION
            "A conceptual row in the f3L3FlowPointThresholdTable."
    INDEX { neIndex, shelfIndex, slotIndex, f3L3FlowPointPortTypeIndex, 
            f3L3FlowPointPortIndex, f3L3FlowPointIndex, f3L3FlowPointStatsIndex, f3L3FlowPointThresholdIndex }
    ::= { f3L3FlowPointThresholdTable 1 }

F3L3FlowPointThresholdEntry ::= SEQUENCE {
    f3L3FlowPointThresholdIndex       Integer32,
    f3L3FlowPointThresholdInterval    CmPmIntervalType,
    f3L3FlowPointThresholdVariable    VariablePointer,
    f3L3FlowPointThresholdValueLo     Unsigned32,
    f3L3FlowPointThresholdValueHi     Unsigned32,
    f3L3FlowPointThresholdMonValue    Counter64
}

f3L3FlowPointThresholdIndex OBJECT-TYPE
    SYNTAX     Integer32 (1..65535)
    MAX-ACCESS read-only
    STATUS     current
    DESCRIPTION
        "An index that uniquely identifies an entry in the
        f3L3FlowPointThresholdTable."
    ::= { f3L3FlowPointThresholdEntry 1 }

f3L3FlowPointThresholdInterval OBJECT-TYPE
    SYNTAX     CmPmIntervalType
    MAX-ACCESS read-only
    STATUS     current
    DESCRIPTION
        "The interval over which monitored value is
        sampled and compared with the specified threshold."
    ::= { f3L3FlowPointThresholdEntry 2 }

f3L3FlowPointThresholdVariable OBJECT-TYPE
    SYNTAX     VariablePointer
    MAX-ACCESS read-only
    STATUS     current
    DESCRIPTION
        "The object identifier of the particular variable to be
        sampled."
    ::= { f3L3FlowPointThresholdEntry 3 }

f3L3FlowPointThresholdValueLo OBJECT-TYPE
    SYNTAX     Unsigned32
    MAX-ACCESS read-write
    STATUS     current
    DESCRIPTION
        "Lower 32 bits of the threshold value."
    ::= { f3L3FlowPointThresholdEntry 4 }

f3L3FlowPointThresholdValueHi OBJECT-TYPE
    SYNTAX     Unsigned32
    MAX-ACCESS read-write
    STATUS     current
    DESCRIPTION
        "Higher 32 bits of the threshold value."
    ::= { f3L3FlowPointThresholdEntry 5 }

f3L3FlowPointThresholdMonValue OBJECT-TYPE
    SYNTAX     Counter64
    MAX-ACCESS read-only
    STATUS     current
    DESCRIPTION
        "Monitored value corresponding to f3L3FlowPointThresholdVariable."
    ::= { f3L3FlowPointThresholdEntry 6 }

--
-- L3 traffic ip interface Current Statistics Table
--
f3L3TrafficIpInterfaceStatsTable OBJECT-TYPE
    SYNTAX      SEQUENCE OF F3L3TrafficIpInterfaceStatsEntry
    MAX-ACCESS  not-accessible
    STATUS      current
    DESCRIPTION
            "A collection of L3 traffic ip interface related statistics.  
             These reflect the current data."
    ::= { f3L3Performance 4 }

f3L3TrafficIpInterfaceStatsEntry OBJECT-TYPE
    SYNTAX      F3L3TrafficIpInterfaceStatsEntry 
    MAX-ACCESS  not-accessible
    STATUS      current
    DESCRIPTION
            "A conceptual row in the f3L3TrafficIpInterfaceStatsTable.
             Entries exist in this table for each L3 traffic ip interface."
    INDEX { neIndex, shelfIndex, slotIndex,
            f3L3FlowPointPortIndex, f3L3FlowPointIndex, f3L3TrafficIPIfIndex, f3L3TrafficIpInterfaceStatsIndex }
    ::= { f3L3TrafficIpInterfaceStatsTable 1 }

F3L3TrafficIpInterfaceStatsEntry ::= SEQUENCE {
    f3L3TrafficIpInterfaceStatsIndex               Integer32,
    f3L3TrafficIpInterfaceStatsIntervalType        CmPmIntervalType,
    f3L3TrafficIpInterfaceStatsValid               TruthValue,
    f3L3TrafficIpInterfaceStatsAction              CmPmBinAction,
    f3L3TrafficIpInterfaceStatsDhcpTx              PerfCounter64,
    f3L3TrafficIpInterfaceStatsDhcpRx              PerfCounter64,
    f3L3TrafficIpInterfaceStatsIcmpTx              PerfCounter64,
    f3L3TrafficIpInterfaceStatsIcmpRx              PerfCounter64,
    f3L3TrafficIpInterfaceStatsArpReqTx            PerfCounter64,
    f3L3TrafficIpInterfaceStatsArpReqRx            PerfCounter64,
    f3L3TrafficIpInterfaceStatsArpReplyTx          PerfCounter64,
    f3L3TrafficIpInterfaceStatsArpReplyRx          PerfCounter64,
    f3L3TrafficIpInterfaceStatsDhcpV6Tx            PerfCounter64,
    f3L3TrafficIpInterfaceStatsDhcpV6Rx            PerfCounter64,
    f3L3TrafficIpInterfaceStatsIcmpV6WONdpTx       PerfCounter64,
    f3L3TrafficIpInterfaceStatsIcmpV6WONdpRx       PerfCounter64,
    f3L3TrafficIpInterfaceStatsNdpNSTx             PerfCounter64,
    f3L3TrafficIpInterfaceStatsNdpNSRx             PerfCounter64,
    f3L3TrafficIpInterfaceStatsNdpNATx             PerfCounter64,
    f3L3TrafficIpInterfaceStatsNdpNARx             PerfCounter64,
    f3L3TrafficIpInterfaceStatsNdpRATx             PerfCounter64,
    f3L3TrafficIpInterfaceStatsNdpRARx             PerfCounter64,
    f3L3TrafficIpInterfaceStatsNdpRSTx             PerfCounter64,
    f3L3TrafficIpInterfaceStatsNdpRSRx             PerfCounter64
}

f3L3TrafficIpInterfaceStatsIndex OBJECT-TYPE
    SYNTAX      Integer32 (1..4)
    MAX-ACCESS  read-only
    STATUS      current
    DESCRIPTION
            "An arbitrary integer index value used to uniquely identify
            this L3 flow point statistics entry. 
            1 - 15min
            2 - 1day
            3 - rollover
            4 - 5min"
    ::= { f3L3TrafficIpInterfaceStatsEntry 1 }

f3L3TrafficIpInterfaceStatsIntervalType OBJECT-TYPE
    SYNTAX      CmPmIntervalType
    MAX-ACCESS  read-only
    STATUS      current
    DESCRIPTION
            "Interval over which Performance Monitoring data is collected."
    ::= { f3L3TrafficIpInterfaceStatsEntry 2 }

f3L3TrafficIpInterfaceStatsValid OBJECT-TYPE
    SYNTAX      TruthValue
    MAX-ACCESS  read-only
    STATUS      current
    DESCRIPTION
            "Indicates the validity of the bin."
    ::= { f3L3TrafficIpInterfaceStatsEntry 3 }

f3L3TrafficIpInterfaceStatsAction OBJECT-TYPE
    SYNTAX      CmPmBinAction
    MAX-ACCESS  read-write
    STATUS      current
    DESCRIPTION
            "Allows the Manager to clear the bin."
    ::= { f3L3TrafficIpInterfaceStatsEntry 4 }

f3L3TrafficIpInterfaceStatsDhcpTx OBJECT-TYPE
     SYNTAX     PerfCounter64
     MAX-ACCESS read-only
     STATUS     current
     DESCRIPTION
         "The number of packets DHCP Transmit."
     ::= { f3L3TrafficIpInterfaceStatsEntry 5 }

f3L3TrafficIpInterfaceStatsDhcpRx OBJECT-TYPE
     SYNTAX     PerfCounter64
     MAX-ACCESS read-only
     STATUS     current
     DESCRIPTION
         "The number of packets DHCP Recieved."
     ::= { f3L3TrafficIpInterfaceStatsEntry 6 }

f3L3TrafficIpInterfaceStatsIcmpTx OBJECT-TYPE
     SYNTAX     PerfCounter64
     MAX-ACCESS read-only
     STATUS     current
     DESCRIPTION
         "The number of packets Icmp protocol transmit."
     ::= { f3L3TrafficIpInterfaceStatsEntry 7 }

f3L3TrafficIpInterfaceStatsIcmpRx OBJECT-TYPE
     SYNTAX     PerfCounter64
     MAX-ACCESS read-only
     STATUS     current
     DESCRIPTION
         "The number of packets Icmp protocol recieved."
     ::= { f3L3TrafficIpInterfaceStatsEntry 8 }

f3L3TrafficIpInterfaceStatsArpReqTx OBJECT-TYPE
     SYNTAX     PerfCounter64
     MAX-ACCESS read-only
     STATUS     current
     DESCRIPTION
         "The number of transmit packets due to ARP request."
     ::= { f3L3TrafficIpInterfaceStatsEntry 9 }

f3L3TrafficIpInterfaceStatsArpReqRx OBJECT-TYPE
     SYNTAX     PerfCounter64
     MAX-ACCESS read-only
     STATUS     current
     DESCRIPTION
         "The number of recieved packets due to ARP request."
     ::= { f3L3TrafficIpInterfaceStatsEntry 10 }

f3L3TrafficIpInterfaceStatsArpReplyTx OBJECT-TYPE
     SYNTAX     PerfCounter64
     MAX-ACCESS read-only
     STATUS     current
     DESCRIPTION
         "The number of transmit packets due to ARP reply."
     ::= { f3L3TrafficIpInterfaceStatsEntry 11 }

f3L3TrafficIpInterfaceStatsArpReplyRx OBJECT-TYPE
     SYNTAX     PerfCounter64
     MAX-ACCESS read-only
     STATUS     current
     DESCRIPTION
         "The number of recieved packets due to ARP reply."
     ::= { f3L3TrafficIpInterfaceStatsEntry 12 }

f3L3TrafficIpInterfaceStatsDhcpV6Tx OBJECT-TYPE
     SYNTAX     PerfCounter64
     MAX-ACCESS read-only
     STATUS     current
     DESCRIPTION
         "The number of packets DHCPv6 Transmit."
     ::= { f3L3TrafficIpInterfaceStatsEntry 13 }

f3L3TrafficIpInterfaceStatsDhcpV6Rx OBJECT-TYPE
     SYNTAX     PerfCounter64
     MAX-ACCESS read-only
     STATUS     current
     DESCRIPTION
         "The number of packets DHCPv6 Recieved."
     ::= { f3L3TrafficIpInterfaceStatsEntry 14 }

f3L3TrafficIpInterfaceStatsIcmpV6WONdpTx OBJECT-TYPE
     SYNTAX     PerfCounter64
     MAX-ACCESS read-only
     STATUS     current
     DESCRIPTION
         "The number of packets Icmpv6 protocol transmit."
     ::= { f3L3TrafficIpInterfaceStatsEntry 15 }

f3L3TrafficIpInterfaceStatsIcmpV6WONdpRx OBJECT-TYPE
     SYNTAX     PerfCounter64
     MAX-ACCESS read-only
     STATUS     current
     DESCRIPTION
         "The number of packets Icmpv6 protocol recieved."
     ::= { f3L3TrafficIpInterfaceStatsEntry 16 }

f3L3TrafficIpInterfaceStatsNdpNSTx OBJECT-TYPE
     SYNTAX     PerfCounter64
     MAX-ACCESS read-only
     STATUS     current
     DESCRIPTION
         "The number of transmit NS message."
     ::= { f3L3TrafficIpInterfaceStatsEntry 17 }

f3L3TrafficIpInterfaceStatsNdpNSRx OBJECT-TYPE
     SYNTAX     PerfCounter64
     MAX-ACCESS read-only
     STATUS     current
     DESCRIPTION
         "The number of recieved NS message."
     ::= { f3L3TrafficIpInterfaceStatsEntry 18 }

f3L3TrafficIpInterfaceStatsNdpNATx OBJECT-TYPE
     SYNTAX     PerfCounter64
     MAX-ACCESS read-only
     STATUS     current
     DESCRIPTION
         "The number of transmit NA message."
     ::= { f3L3TrafficIpInterfaceStatsEntry 19 }

f3L3TrafficIpInterfaceStatsNdpNARx OBJECT-TYPE
     SYNTAX     PerfCounter64
     MAX-ACCESS read-only
     STATUS     current
     DESCRIPTION
         "The number of recieved NA message."
     ::= { f3L3TrafficIpInterfaceStatsEntry 20 }

f3L3TrafficIpInterfaceStatsNdpRATx OBJECT-TYPE
     SYNTAX     PerfCounter64
     MAX-ACCESS read-only
     STATUS     current
     DESCRIPTION
         "The number of transmit RA message."
     ::= { f3L3TrafficIpInterfaceStatsEntry 21 }

f3L3TrafficIpInterfaceStatsNdpRARx OBJECT-TYPE
     SYNTAX     PerfCounter64
     MAX-ACCESS read-only
     STATUS     current
     DESCRIPTION
         "The number of recieved RA message."
     ::= { f3L3TrafficIpInterfaceStatsEntry 22 }

f3L3TrafficIpInterfaceStatsNdpRSTx OBJECT-TYPE
     SYNTAX     PerfCounter64
     MAX-ACCESS read-only
     STATUS     current
     DESCRIPTION
         "The number of transmit RS message."
     ::= { f3L3TrafficIpInterfaceStatsEntry 23 }

f3L3TrafficIpInterfaceStatsNdpRSRx OBJECT-TYPE
     SYNTAX     PerfCounter64
     MAX-ACCESS read-only
     STATUS     current
     DESCRIPTION
         "The number of recieved RS message."
     ::= { f3L3TrafficIpInterfaceStatsEntry 24 }


--
-- L3 traffic ip interface history Statistics Table
--
f3L3TrafficIpInterfaceHistoryTable OBJECT-TYPE
    SYNTAX      SEQUENCE OF F3L3TrafficIpInterfaceHistoryEntry
    MAX-ACCESS  not-accessible
    STATUS      current
    DESCRIPTION
            "A collection of L3 traffic ip interface related history statistics.  
             These reflect the history data."
    ::= { f3L3Performance 5 }

f3L3TrafficIpInterfaceHistoryEntry OBJECT-TYPE
    SYNTAX      F3L3TrafficIpInterfaceHistoryEntry 
    MAX-ACCESS  not-accessible
    STATUS      current
    DESCRIPTION
            "A conceptual row in the f3L3TrafficIpInterfaceHistoryTable.
             Entries exist in this table for each L3 traffic ip interface."
    INDEX { neIndex, shelfIndex, slotIndex, 
            f3L3FlowPointPortIndex, f3L3FlowPointIndex, f3L3TrafficIPIfIndex,
            f3L3TrafficIpInterfaceStatsIndex, f3L3TrafficIpInterfaceHistoryIndex }
    ::= { f3L3TrafficIpInterfaceHistoryTable 1 }

F3L3TrafficIpInterfaceHistoryEntry ::= SEQUENCE {
    f3L3TrafficIpInterfaceHistoryIndex               Integer32,
    f3L3TrafficIpInterfaceHistoryTime                DateAndTime,
    f3L3TrafficIpInterfaceHistoryValid               TruthValue,
    f3L3TrafficIpInterfaceHistoryAction              CmPmBinAction,
    f3L3TrafficIpInterfaceHistoryDhcpTx              PerfCounter64,
    f3L3TrafficIpInterfaceHistoryDhcpRx              PerfCounter64,
    f3L3TrafficIpInterfaceHistoryIcmpTx              PerfCounter64,
    f3L3TrafficIpInterfaceHistoryIcmpRx              PerfCounter64,
    f3L3TrafficIpInterfaceHistoryArpReqTx            PerfCounter64,
    f3L3TrafficIpInterfaceHistoryArpReqRx            PerfCounter64,
    f3L3TrafficIpInterfaceHistoryArpReplyTx          PerfCounter64,
    f3L3TrafficIpInterfaceHistoryArpReplyRx          PerfCounter64,
    f3L3TrafficIpInterfaceHistoryDhcpV6Tx            PerfCounter64,
    f3L3TrafficIpInterfaceHistoryDhcpV6Rx            PerfCounter64,
    f3L3TrafficIpInterfaceHistoryIcmpV6WONdpTx       PerfCounter64,
    f3L3TrafficIpInterfaceHistoryIcmpV6WONdpRx       PerfCounter64,
    f3L3TrafficIpInterfaceHistoryNdpNSTx             PerfCounter64,
    f3L3TrafficIpInterfaceHistoryNdpNSRx             PerfCounter64,
    f3L3TrafficIpInterfaceHistoryNdpNATx             PerfCounter64,
    f3L3TrafficIpInterfaceHistoryNdpNARx             PerfCounter64,
    f3L3TrafficIpInterfaceHistoryNdpRATx             PerfCounter64,
    f3L3TrafficIpInterfaceHistoryNdpRARx             PerfCounter64,
    f3L3TrafficIpInterfaceHistoryNdpRSTx             PerfCounter64,
    f3L3TrafficIpInterfaceHistoryNdpRSRx             PerfCounter64
}

f3L3TrafficIpInterfaceHistoryIndex OBJECT-TYPE
    SYNTAX      Integer32 (1..65535)
    MAX-ACCESS  read-only
    STATUS      current
    DESCRIPTION
            "An arbitrary integer index value used to uniquely identify
            the history bin"
    ::= { f3L3TrafficIpInterfaceHistoryEntry 1 }

f3L3TrafficIpInterfaceHistoryTime OBJECT-TYPE
    SYNTAX      DateAndTime
    MAX-ACCESS  read-only
    STATUS      current
    DESCRIPTION
            "Indicates the time of history bin creation." 
    ::= { f3L3TrafficIpInterfaceHistoryEntry 2 }

f3L3TrafficIpInterfaceHistoryValid OBJECT-TYPE
    SYNTAX      TruthValue
    MAX-ACCESS  read-only
    STATUS      current
    DESCRIPTION
            "Indicates the validity of the bin."
    ::= { f3L3TrafficIpInterfaceHistoryEntry 3 }

f3L3TrafficIpInterfaceHistoryAction OBJECT-TYPE
    SYNTAX      CmPmBinAction
    MAX-ACCESS  read-write
    STATUS      current
    DESCRIPTION
            "Allows the Manager to clear the bin."
    ::= { f3L3TrafficIpInterfaceHistoryEntry 4 }

f3L3TrafficIpInterfaceHistoryDhcpTx OBJECT-TYPE
     SYNTAX     PerfCounter64
     MAX-ACCESS read-only
     STATUS     current
     DESCRIPTION
         "The number of packets DHCP Transmit."
     ::= { f3L3TrafficIpInterfaceHistoryEntry 5 }

f3L3TrafficIpInterfaceHistoryDhcpRx OBJECT-TYPE
     SYNTAX     PerfCounter64
     MAX-ACCESS read-only
     STATUS     current
     DESCRIPTION
         "The number of packets DHCP Recieved."
     ::= { f3L3TrafficIpInterfaceHistoryEntry 6 }

f3L3TrafficIpInterfaceHistoryIcmpTx OBJECT-TYPE
     SYNTAX     PerfCounter64
     MAX-ACCESS read-only
     STATUS     current
     DESCRIPTION
         "The number of packets Icmp protocol transmit."
     ::= { f3L3TrafficIpInterfaceHistoryEntry 7 }

f3L3TrafficIpInterfaceHistoryIcmpRx OBJECT-TYPE
     SYNTAX     PerfCounter64
     MAX-ACCESS read-only
     STATUS     current
     DESCRIPTION
         "The number of packets Icmp protocol recieved."
     ::= { f3L3TrafficIpInterfaceHistoryEntry 8 }

f3L3TrafficIpInterfaceHistoryArpReqTx OBJECT-TYPE
     SYNTAX     PerfCounter64
     MAX-ACCESS read-only
     STATUS     current
     DESCRIPTION
         "The number of transmit packets due to ARP request."
     ::= { f3L3TrafficIpInterfaceHistoryEntry 9 }

f3L3TrafficIpInterfaceHistoryArpReqRx OBJECT-TYPE
     SYNTAX     PerfCounter64
     MAX-ACCESS read-only
     STATUS     current
     DESCRIPTION
         " the number of recieved packets due to ARP request."
     ::= { f3L3TrafficIpInterfaceHistoryEntry 10 }

f3L3TrafficIpInterfaceHistoryArpReplyTx OBJECT-TYPE
     SYNTAX     PerfCounter64
     MAX-ACCESS read-only
     STATUS     current
     DESCRIPTION
         "The number of transmit packets due to ARP reply."
     ::= { f3L3TrafficIpInterfaceHistoryEntry 11 }

f3L3TrafficIpInterfaceHistoryArpReplyRx OBJECT-TYPE
     SYNTAX     PerfCounter64
     MAX-ACCESS read-only
     STATUS     current
     DESCRIPTION
         " the number of recieved packets due to ARP reply."
     ::= { f3L3TrafficIpInterfaceHistoryEntry 12 }

f3L3TrafficIpInterfaceHistoryDhcpV6Tx OBJECT-TYPE
     SYNTAX     PerfCounter64
     MAX-ACCESS read-only
     STATUS     current
     DESCRIPTION
         "The number of packets DHCPv6 Transmit."
     ::= { f3L3TrafficIpInterfaceHistoryEntry 13 }

f3L3TrafficIpInterfaceHistoryDhcpV6Rx OBJECT-TYPE
     SYNTAX     PerfCounter64
     MAX-ACCESS read-only
     STATUS     current
     DESCRIPTION
         "The number of packets DHCPv6 Recieved."
     ::= { f3L3TrafficIpInterfaceHistoryEntry 14 }

f3L3TrafficIpInterfaceHistoryIcmpV6WONdpTx OBJECT-TYPE
     SYNTAX     PerfCounter64
     MAX-ACCESS read-only
     STATUS     current
     DESCRIPTION
         "The number of packets Icmpv6 protocol transmit."
     ::= { f3L3TrafficIpInterfaceHistoryEntry 15 }

f3L3TrafficIpInterfaceHistoryIcmpV6WONdpRx OBJECT-TYPE
     SYNTAX     PerfCounter64
     MAX-ACCESS read-only
     STATUS     current
     DESCRIPTION
         "The number of packets Icmpv6 protocol recieved."
     ::= { f3L3TrafficIpInterfaceHistoryEntry 16 }

f3L3TrafficIpInterfaceHistoryNdpNSTx OBJECT-TYPE
     SYNTAX     PerfCounter64
     MAX-ACCESS read-only
     STATUS     current
     DESCRIPTION
         "The number of transmit NS message."
     ::= { f3L3TrafficIpInterfaceHistoryEntry 17 }

f3L3TrafficIpInterfaceHistoryNdpNSRx OBJECT-TYPE
     SYNTAX     PerfCounter64
     MAX-ACCESS read-only
     STATUS     current
     DESCRIPTION
         "The number of recieved NS message."
     ::= { f3L3TrafficIpInterfaceHistoryEntry 18 }

f3L3TrafficIpInterfaceHistoryNdpNATx OBJECT-TYPE
     SYNTAX     PerfCounter64
     MAX-ACCESS read-only
     STATUS     current
     DESCRIPTION
         "The number of transmit NA message."
     ::= { f3L3TrafficIpInterfaceHistoryEntry 19 }

f3L3TrafficIpInterfaceHistoryNdpNARx OBJECT-TYPE
     SYNTAX     PerfCounter64
     MAX-ACCESS read-only
     STATUS     current
     DESCRIPTION
         "The number of recieved NA message."
     ::= { f3L3TrafficIpInterfaceHistoryEntry 20 }

f3L3TrafficIpInterfaceHistoryNdpRATx OBJECT-TYPE
     SYNTAX     PerfCounter64
     MAX-ACCESS read-only
     STATUS     current
     DESCRIPTION
         "The number of transmit RA message."
     ::= { f3L3TrafficIpInterfaceHistoryEntry 21 }

f3L3TrafficIpInterfaceHistoryNdpRARx OBJECT-TYPE
     SYNTAX     PerfCounter64
     MAX-ACCESS read-only
     STATUS     current
     DESCRIPTION
         "The number of recieved RA message."
     ::= { f3L3TrafficIpInterfaceHistoryEntry 22 }

f3L3TrafficIpInterfaceHistoryNdpRSTx OBJECT-TYPE
     SYNTAX     PerfCounter64
     MAX-ACCESS read-only
     STATUS     current
     DESCRIPTION
         "The number of transmit RS message."
     ::= { f3L3TrafficIpInterfaceHistoryEntry 23 }

f3L3TrafficIpInterfaceHistoryNdpRSRx OBJECT-TYPE
     SYNTAX     PerfCounter64
     MAX-ACCESS read-only
     STATUS     current
     DESCRIPTION
         "The number of recieved RS message."
     ::= { f3L3TrafficIpInterfaceHistoryEntry 24 }


--
-- L3 traffic ip interface Threshold Table
--
f3L3TrafficIpInterfaceThresholdTable OBJECT-TYPE
    SYNTAX      SEQUENCE OF F3L3TrafficIpInterfaceThresholdEntry
    MAX-ACCESS  not-accessible
    STATUS      current
    DESCRIPTION
            "A table of entries that allow manageability of L3 traffic ip interface Thresholds."
    ::= { f3L3Performance 6 }

f3L3TrafficIpInterfaceThresholdEntry OBJECT-TYPE
    SYNTAX      F3L3TrafficIpInterfaceThresholdEntry
    MAX-ACCESS  not-accessible
    STATUS      current
    DESCRIPTION
            "A conceptual row in the f3L3TrafficIpInterfaceThresholdTable."
    INDEX { neIndex, shelfIndex, slotIndex, 
            f3L3FlowPointPortIndex, f3L3FlowPointIndex, f3L3TrafficIPIfIndex,
            f3L3TrafficIpInterfaceStatsIndex, f3L3TrafficIpInterfaceThresholdIndex }
    ::= { f3L3TrafficIpInterfaceThresholdTable 1 }

F3L3TrafficIpInterfaceThresholdEntry ::= SEQUENCE {
    f3L3TrafficIpInterfaceThresholdIndex       Integer32,
    f3L3TrafficIpInterfaceThresholdInterval    CmPmIntervalType,
    f3L3TrafficIpInterfaceThresholdVariable    VariablePointer,
    f3L3TrafficIpInterfaceThresholdValueLo     Unsigned32,
    f3L3TrafficIpInterfaceThresholdValueHi     Unsigned32,
    f3L3TrafficIpInterfaceThresholdMonValue    Counter64
}

f3L3TrafficIpInterfaceThresholdIndex OBJECT-TYPE
    SYNTAX     Integer32 (1..65535)
    MAX-ACCESS read-only
    STATUS     current
    DESCRIPTION
        "An index that uniquely identifies an entry in the
        f3L3TrafficIpInterfaceThresholdTable."
    ::= { f3L3TrafficIpInterfaceThresholdEntry 1 }

f3L3TrafficIpInterfaceThresholdInterval OBJECT-TYPE
    SYNTAX     CmPmIntervalType
    MAX-ACCESS read-only
    STATUS     current
    DESCRIPTION
        "The interval over which monitored value is
        sampled and compared with the specified threshold."
    ::= { f3L3TrafficIpInterfaceThresholdEntry 2 }

f3L3TrafficIpInterfaceThresholdVariable OBJECT-TYPE
    SYNTAX     VariablePointer
    MAX-ACCESS read-only
    STATUS     current
    DESCRIPTION
        "The object identifier of the particular variable to be
        sampled."
    ::= { f3L3TrafficIpInterfaceThresholdEntry 3 }

f3L3TrafficIpInterfaceThresholdValueLo OBJECT-TYPE
    SYNTAX     Unsigned32
    MAX-ACCESS read-write
    STATUS     current
    DESCRIPTION
        "Lower 32 bits of the threshold value."
    ::= { f3L3TrafficIpInterfaceThresholdEntry 4 }

f3L3TrafficIpInterfaceThresholdValueHi OBJECT-TYPE
    SYNTAX     Unsigned32
    MAX-ACCESS read-write
    STATUS     current
    DESCRIPTION
        "Higher 32 bits of the threshold value."
    ::= { f3L3TrafficIpInterfaceThresholdEntry 5 }

f3L3TrafficIpInterfaceThresholdMonValue OBJECT-TYPE
    SYNTAX     Counter64
    MAX-ACCESS read-only
    STATUS     current
    DESCRIPTION
        "Monitored value corresponding to f3L3TrafficIpInterfaceThresholdVariable."
    ::= { f3L3TrafficIpInterfaceThresholdEntry 6 }

--
-- L3 acl rule Current Statistics Table
--
f3L3AclRuleStatsTable OBJECT-TYPE
    SYNTAX      SEQUENCE OF F3L3AclRuleStatsEntry
    MAX-ACCESS  not-accessible
    STATUS      current
    DESCRIPTION
            "A collection of L3 acl rule related statistics.  
             These reflect the current data."
    ::= { f3L3Performance 7 }

f3L3AclRuleStatsEntry OBJECT-TYPE
    SYNTAX      F3L3AclRuleStatsEntry 
    MAX-ACCESS  not-accessible
    STATUS      current
    DESCRIPTION
            "A conceptual row in the f3L3AclRuleStatsTable.
             Entries exist in this table for each Acl rule."
    INDEX { neIndex, shelfIndex, slotIndex,
            f3L3FlowPointPortIndex, f3L3AclRuleParentIndex, f3L3AclRuleIndex, f3L3AclRuleStatsIndex }
    ::= { f3L3AclRuleStatsTable 1 }

F3L3AclRuleStatsEntry ::= SEQUENCE {
    f3L3AclRuleStatsIndex               Integer32,
    f3L3AclRuleStatsIntervalType        CmPmIntervalType,
    f3L3AclRuleStatsValid               TruthValue,
    f3L3AclRuleStatsAction              CmPmBinAction,
    f3L3AclRuleStatsRuleMatch           PerfCounter64
}

f3L3AclRuleStatsIndex OBJECT-TYPE
    SYNTAX      Integer32 (1..4)
    MAX-ACCESS  read-only
    STATUS      current
    DESCRIPTION
            "An arbitrary integer index value used to uniquely identify
            this L3 flow point statistics entry. 
            1 - 15min
            2 - 1day
            3 - rollover
            4 - 5min"
    ::= { f3L3AclRuleStatsEntry 1 }

f3L3AclRuleStatsIntervalType OBJECT-TYPE
    SYNTAX      CmPmIntervalType
    MAX-ACCESS  read-only
    STATUS      current
    DESCRIPTION
            "Interval over which Performance Monitoring data is collected."
    ::= { f3L3AclRuleStatsEntry 2 }

f3L3AclRuleStatsValid OBJECT-TYPE
    SYNTAX      TruthValue
    MAX-ACCESS  read-only
    STATUS      current
    DESCRIPTION
            "Indicates the validity of the bin."
    ::= { f3L3AclRuleStatsEntry 3 }

f3L3AclRuleStatsAction OBJECT-TYPE
    SYNTAX      CmPmBinAction
    MAX-ACCESS  read-write
    STATUS      current
    DESCRIPTION
            "Allows the Manager to clear the bin."
    ::= { f3L3AclRuleStatsEntry 4 }

f3L3AclRuleStatsRuleMatch OBJECT-TYPE
     SYNTAX     PerfCounter64
     MAX-ACCESS read-only
     STATUS     current
     DESCRIPTION
         "The number of packets matching the ACL rule."
     ::= { f3L3AclRuleStatsEntry 5 }

--
-- L3 acl rule history Statistics Table
--
f3L3AclRuleHistoryTable OBJECT-TYPE
    SYNTAX      SEQUENCE OF F3L3AclRuleHistoryEntry
    MAX-ACCESS  not-accessible
    STATUS      current
    DESCRIPTION
            "A collection of L3 acl rule related history statistics.  
             These reflect the history data."
    ::= { f3L3Performance 8 }

f3L3AclRuleHistoryEntry OBJECT-TYPE
    SYNTAX      F3L3AclRuleHistoryEntry 
    MAX-ACCESS  not-accessible
    STATUS      current
    DESCRIPTION
            "A conceptual row in the f3L3AclRuleHistoryTable.
             Entries exist in this table for each L3 acl rule."
    INDEX { neIndex, shelfIndex, slotIndex,
            f3L3FlowPointPortIndex, f3L3AclRuleParentIndex, f3L3AclRuleIndex,
            f3L3AclRuleStatsIndex, f3L3AclRuleHistoryIndex }
    ::= { f3L3AclRuleHistoryTable 1 }

F3L3AclRuleHistoryEntry ::= SEQUENCE {
    f3L3AclRuleHistoryIndex               Integer32,
    f3L3AclRuleHistoryTime                DateAndTime,
    f3L3AclRuleHistoryValid               TruthValue,
    f3L3AclRuleHistoryAction              CmPmBinAction,
    f3L3AclRuleHistoryRuleMatch           PerfCounter64
}

f3L3AclRuleHistoryIndex OBJECT-TYPE
    SYNTAX      Integer32 (1..65535)
    MAX-ACCESS  read-only
    STATUS      current
    DESCRIPTION
            "An arbitrary integer index value used to uniquely identify
            the history bin."
    ::= { f3L3AclRuleHistoryEntry 1 }

f3L3AclRuleHistoryTime OBJECT-TYPE
    SYNTAX      DateAndTime
    MAX-ACCESS  read-only
    STATUS      current
    DESCRIPTION
            "Indicates the time of history bin creation." 
    ::= { f3L3AclRuleHistoryEntry 2 }

f3L3AclRuleHistoryValid OBJECT-TYPE
    SYNTAX      TruthValue
    MAX-ACCESS  read-only
    STATUS      current
    DESCRIPTION
            "Indicates the validity of the bin."
    ::= { f3L3AclRuleHistoryEntry 3 }

f3L3AclRuleHistoryAction OBJECT-TYPE
    SYNTAX      CmPmBinAction
    MAX-ACCESS  read-write
    STATUS      current
    DESCRIPTION
            "Allows the Manager to clear the bin."
    ::= { f3L3AclRuleHistoryEntry 4 }

f3L3AclRuleHistoryRuleMatch OBJECT-TYPE
     SYNTAX     PerfCounter64
     MAX-ACCESS read-only
     STATUS     current
     DESCRIPTION
         "The number of packets matching acl rule."
     ::= { f3L3AclRuleHistoryEntry 5 }

--
-- L3 acl rule Threshold Table
--
f3L3AclRuleThresholdTable OBJECT-TYPE
    SYNTAX      SEQUENCE OF F3L3AclRuleThresholdEntry
    MAX-ACCESS  not-accessible
    STATUS      current
    DESCRIPTION
            "A table of entries that allow manageability of L3 acl rule Thresholds."
    ::= { f3L3Performance 9 }

f3L3AclRuleThresholdEntry OBJECT-TYPE
    SYNTAX      F3L3AclRuleThresholdEntry
    MAX-ACCESS  not-accessible
    STATUS      current
    DESCRIPTION
            "A conceptual row in the f3L3AclRuleThresholdTable."
    INDEX { neIndex, shelfIndex, slotIndex,
            f3L3FlowPointPortIndex, f3L3AclRuleParentIndex, f3L3AclRuleIndex,
            f3L3AclRuleStatsIndex, f3L3AclRuleThresholdIndex }
    ::= { f3L3AclRuleThresholdTable 1 }

F3L3AclRuleThresholdEntry ::= SEQUENCE {
    f3L3AclRuleThresholdIndex       Integer32,
    f3L3AclRuleThresholdInterval    CmPmIntervalType,
    f3L3AclRuleThresholdVariable    VariablePointer,
    f3L3AclRuleThresholdValueLo     Unsigned32,
    f3L3AclRuleThresholdValueHi     Unsigned32,
    f3L3AclRuleThresholdMonValue    Counter64
}

f3L3AclRuleThresholdIndex OBJECT-TYPE
    SYNTAX     Integer32 (1..65535)
    MAX-ACCESS read-only
    STATUS     current
    DESCRIPTION
        "An index that uniquely identifies an entry in the
        f3L3AclRuleThresholdTable."
    ::= { f3L3AclRuleThresholdEntry 1 }

f3L3AclRuleThresholdInterval OBJECT-TYPE
    SYNTAX     CmPmIntervalType
    MAX-ACCESS read-only
    STATUS     current
    DESCRIPTION
        "The interval over which monitored value is
        sampled and compared with the specified threshold."
    ::= { f3L3AclRuleThresholdEntry 2 }

f3L3AclRuleThresholdVariable OBJECT-TYPE
    SYNTAX     VariablePointer
    MAX-ACCESS read-only
    STATUS     current
    DESCRIPTION
        "The object identifier of the particular variable to be
        sampled."
    ::= { f3L3AclRuleThresholdEntry 3 }

f3L3AclRuleThresholdValueLo OBJECT-TYPE
    SYNTAX     Unsigned32
    MAX-ACCESS read-write
    STATUS     current
    DESCRIPTION
        "Lower 32 bits of the threshold value."
    ::= { f3L3AclRuleThresholdEntry 4 }

f3L3AclRuleThresholdValueHi OBJECT-TYPE
    SYNTAX     Unsigned32
    MAX-ACCESS read-write
    STATUS     current
    DESCRIPTION
        "Higher 32 bits of the threshold value."
    ::= { f3L3AclRuleThresholdEntry 5 }

f3L3AclRuleThresholdMonValue OBJECT-TYPE
    SYNTAX     Counter64
    MAX-ACCESS read-only
    STATUS     current
    DESCRIPTION
        "Monitored value corresponding to f3L3AclRuleThresholdVariable."
    ::= { f3L3AclRuleThresholdEntry 6 }

--
-- Quality of Service(QOS) Policer Current Statistics Table
--
f3L3QosPolicerStatsTable OBJECT-TYPE
    SYNTAX      SEQUENCE OF F3L3QosPolicerStatsEntry
    MAX-ACCESS  not-accessible
    STATUS      current
    DESCRIPTION
            "A collection of QOS Policer statistics.  
             These reflect the current data."
    ::= { f3L3Performance 10 }

f3L3QosPolicerStatsEntry OBJECT-TYPE
    SYNTAX      F3L3QosPolicerStatsEntry 
    MAX-ACCESS  not-accessible
    STATUS      current
    DESCRIPTION
            "A conceptual row in the f3L3QosPolicerStatsTable.
             Entries exist in this table for each l3 flow point policer."
    INDEX { neIndex, shelfIndex, slotIndex, f3L3FlowPointPortTypeIndex, 
            f3L3FlowPointPortIndex, f3L3FlowPointIndex, f3L3QosPolicerIndex,
            f3L3QosPolicerStatsIndex }
    ::= { f3L3QosPolicerStatsTable 1 }

F3L3QosPolicerStatsEntry ::= SEQUENCE {
    f3L3QosPolicerStatsIndex           Integer32,
    f3L3QosPolicerStatsIntervalType    CmPmIntervalType,
    f3L3QosPolicerStatsValid           TruthValue,
    f3L3QosPolicerStatsAction          CmPmBinAction,
    f3L3QosPolicerStatsFMG             PerfCounter64,
    f3L3QosPolicerStatsFMY             PerfCounter64,
    f3L3QosPolicerStatsFMYD            PerfCounter64,
    f3L3QosPolicerStatsFMRD            PerfCounter64,
    f3L3QosPolicerStatsBytesIn         PerfCounter64,
    f3L3QosPolicerStatsBytesOut        PerfCounter64,
    f3L3QosPolicerStatsABR             PerfCounter64
}

f3L3QosPolicerStatsIndex OBJECT-TYPE
    SYNTAX      Integer32 (1..65535)
    MAX-ACCESS  read-only
    STATUS      current
    DESCRIPTION
            "An integer index value used to uniquely identify
            this QOS Policer statistics entry.
            1 - 15min
            2 - 1day
            3 - rollover
            4 - 5min"
    ::= { f3L3QosPolicerStatsEntry 1 }

f3L3QosPolicerStatsIntervalType OBJECT-TYPE
    SYNTAX      CmPmIntervalType
    MAX-ACCESS  read-only
    STATUS      current
    DESCRIPTION
            "Interval over which Performance Monitoring data is collected."
    ::= { f3L3QosPolicerStatsEntry 2 }

f3L3QosPolicerStatsValid OBJECT-TYPE
    SYNTAX      TruthValue
    MAX-ACCESS  read-only
    STATUS      current
    DESCRIPTION
            "Indicates the validity of the bin."
    ::= { f3L3QosPolicerStatsEntry 3 }

f3L3QosPolicerStatsAction OBJECT-TYPE
    SYNTAX      CmPmBinAction
    MAX-ACCESS  read-write
    STATUS      current
    DESCRIPTION
            "Allows the Manager to clear the bin."
    ::= { f3L3QosPolicerStatsEntry 4 }

f3L3QosPolicerStatsFMG OBJECT-TYPE
     SYNTAX     PerfCounter64
     MAX-ACCESS read-only
     STATUS     current
     DESCRIPTION
         "Frames Marked Green."
     ::= { f3L3QosPolicerStatsEntry 5 }

f3L3QosPolicerStatsFMY OBJECT-TYPE
     SYNTAX     PerfCounter64
     MAX-ACCESS read-only
     STATUS     current
     DESCRIPTION
         "Frames Marked Yellow."
     ::= { f3L3QosPolicerStatsEntry 6 }

f3L3QosPolicerStatsFMYD OBJECT-TYPE
     SYNTAX     PerfCounter64
     MAX-ACCESS read-only
     STATUS     deprecated
     DESCRIPTION
         "Frames Marked Yellow and Dropped."
     ::= { f3L3QosPolicerStatsEntry 7 }

f3L3QosPolicerStatsFMRD OBJECT-TYPE
     SYNTAX     PerfCounter64
     MAX-ACCESS read-only
     STATUS     current
     DESCRIPTION
         "Frames Marked Red and Discarded."
     ::= { f3L3QosPolicerStatsEntry 8 }

f3L3QosPolicerStatsBytesIn OBJECT-TYPE
     SYNTAX     PerfCounter64
     MAX-ACCESS read-only
     STATUS     current
     DESCRIPTION
         "Number of bytes received by the Policer."
     ::= { f3L3QosPolicerStatsEntry 9 }

f3L3QosPolicerStatsBytesOut OBJECT-TYPE
     SYNTAX     PerfCounter64
     MAX-ACCESS read-only
     STATUS     current
     DESCRIPTION
         "Number of bytes transmitted by the Policer."
     ::= { f3L3QosPolicerStatsEntry 10 }

f3L3QosPolicerStatsABR OBJECT-TYPE
     SYNTAX     PerfCounter64
     MAX-ACCESS read-only
     STATUS     current
     DESCRIPTION
         "Average Bit Rate  on the Policer."
     ::= { f3L3QosPolicerStatsEntry 11 }


--
-- Quality of Service(QOS) Policer History Statistics Table
--
f3L3QosPolicerHistoryTable OBJECT-TYPE
    SYNTAX      SEQUENCE OF F3L3QosPolicerHistoryEntry
    MAX-ACCESS  not-accessible
    STATUS      current
    DESCRIPTION
            "A collection of QOS Policer statistics.  
             These reflect the current data."
    ::= { f3L3Performance 11 }

f3L3QosPolicerHistoryEntry OBJECT-TYPE
    SYNTAX      F3L3QosPolicerHistoryEntry 
    MAX-ACCESS  not-accessible
    STATUS      current
    DESCRIPTION
            "A conceptual row in the f3L3QosPolicerHistoryTable.
             Entries exist in this table for each flow point policer."
    INDEX { neIndex, shelfIndex, slotIndex, f3L3FlowPointPortTypeIndex, 
            f3L3FlowPointPortIndex, f3L3FlowPointIndex, f3L3QosPolicerIndex,
            f3L3QosPolicerStatsIndex, f3L3QosPolicerHistoryIndex }
    ::= { f3L3QosPolicerHistoryTable 1 }

F3L3QosPolicerHistoryEntry ::= SEQUENCE {
    f3L3QosPolicerHistoryIndex           Integer32,
    f3L3QosPolicerHistoryTime            DateAndTime,
    f3L3QosPolicerHistoryValid           TruthValue,
    f3L3QosPolicerHistoryAction          CmPmBinAction,
    f3L3QosPolicerHistoryFMG             PerfCounter64,
    f3L3QosPolicerHistoryFMY             PerfCounter64,
    f3L3QosPolicerHistoryFMYD            PerfCounter64,
    f3L3QosPolicerHistoryFMRD            PerfCounter64,
    f3L3QosPolicerHistoryBytesIn         PerfCounter64,
    f3L3QosPolicerHistoryBytesOut        PerfCounter64,
    f3L3QosPolicerHistoryABR             PerfCounter64
}

f3L3QosPolicerHistoryIndex OBJECT-TYPE
    SYNTAX      Integer32 (1..65535)
    MAX-ACCESS  read-only
    STATUS      current
    DESCRIPTION
            "An arbitrary integer index value used to uniquely identify
            this QOS Policer history entry."
    ::= { f3L3QosPolicerHistoryEntry 1 }

f3L3QosPolicerHistoryTime OBJECT-TYPE
    SYNTAX      DateAndTime
    MAX-ACCESS  read-only
    STATUS      current
    DESCRIPTION
            "Indicates the time of history bin creation." 
    ::= { f3L3QosPolicerHistoryEntry 2 }

f3L3QosPolicerHistoryValid OBJECT-TYPE
    SYNTAX      TruthValue
    MAX-ACCESS  read-only
    STATUS      current
    DESCRIPTION
            "Indicates the validity of the bin."
    ::= { f3L3QosPolicerHistoryEntry 3 }

f3L3QosPolicerHistoryAction OBJECT-TYPE
    SYNTAX      CmPmBinAction
    MAX-ACCESS  read-write
    STATUS      current
    DESCRIPTION
            "Allows the Manager to clear the bin."
    ::= { f3L3QosPolicerHistoryEntry 4 }

f3L3QosPolicerHistoryFMG OBJECT-TYPE
     SYNTAX     PerfCounter64
     MAX-ACCESS read-only
     STATUS     current
     DESCRIPTION
         "Frames Marked Green."
     ::= { f3L3QosPolicerHistoryEntry 5 }

f3L3QosPolicerHistoryFMY OBJECT-TYPE
     SYNTAX     PerfCounter64
     MAX-ACCESS read-only
     STATUS     current
     DESCRIPTION
         "Frames Marked Yellow."
     ::= { f3L3QosPolicerHistoryEntry 6 }

f3L3QosPolicerHistoryFMYD OBJECT-TYPE
     SYNTAX     PerfCounter64
     MAX-ACCESS read-only
     STATUS     deprecated
     DESCRIPTION
         "Frames Marked Yellow and Dropped."
     ::= { f3L3QosPolicerHistoryEntry 7 }

f3L3QosPolicerHistoryFMRD OBJECT-TYPE
     SYNTAX     PerfCounter64
     MAX-ACCESS read-only
     STATUS     current
     DESCRIPTION
         "Frames Marked Red and Discarded."
     ::= { f3L3QosPolicerHistoryEntry 8 }

f3L3QosPolicerHistoryBytesIn OBJECT-TYPE
     SYNTAX     PerfCounter64
     MAX-ACCESS read-only
     STATUS     current
     DESCRIPTION
         "Number of bytes received by the Policer."
     ::= { f3L3QosPolicerHistoryEntry 9 }

f3L3QosPolicerHistoryBytesOut OBJECT-TYPE
     SYNTAX     PerfCounter64
     MAX-ACCESS read-only
     STATUS     current
     DESCRIPTION
         "Number of bytes transmitted by the Policer."
     ::= { f3L3QosPolicerHistoryEntry 10 }

f3L3QosPolicerHistoryABR OBJECT-TYPE
     SYNTAX     PerfCounter64
     MAX-ACCESS read-only
     STATUS     current
     DESCRIPTION
         "Average Bit Rate  on the Policer."
     ::= { f3L3QosPolicerHistoryEntry 11 }

--
-- QOS Policer Threshold Table
--
f3L3QosPolicerThresholdTable OBJECT-TYPE
    SYNTAX      SEQUENCE OF F3L3QosPolicerThresholdEntry
    MAX-ACCESS  not-accessible
    STATUS      current
    DESCRIPTION
            "A table of entries that allow manageability of QOS
             Policer Thresholds."
    ::= { f3L3Performance 12 }

f3L3QosPolicerThresholdEntry OBJECT-TYPE
    SYNTAX      F3L3QosPolicerThresholdEntry
    MAX-ACCESS  not-accessible
    STATUS      current
    DESCRIPTION
            "A conceptual row in the f3L3QosPolicerThresholdTable."
    INDEX { neIndex, shelfIndex, slotIndex, f3L3FlowPointPortTypeIndex, 
            f3L3FlowPointPortIndex, f3L3FlowPointIndex, f3L3QosPolicerIndex,
            f3L3QosPolicerStatsIndex, f3L3QosPolicerThresholdIndex }
    ::= { f3L3QosPolicerThresholdTable 1 }

F3L3QosPolicerThresholdEntry ::= SEQUENCE {
    f3L3QosPolicerThresholdIndex       Integer32,
    f3L3QosPolicerThresholdInterval    CmPmIntervalType,
    f3L3QosPolicerThresholdVariable    VariablePointer,
    f3L3QosPolicerThresholdValueLo     Unsigned32,
    f3L3QosPolicerThresholdValueHi     Unsigned32,
    f3L3QosPolicerThresholdMonValue    Counter64
}

f3L3QosPolicerThresholdIndex OBJECT-TYPE
    SYNTAX     Integer32 (1..65535)
    MAX-ACCESS read-only
    STATUS     current
    DESCRIPTION
        "An index that uniquely identifies an entry in the
        f3L3QosPolicerThresholdTable."
    ::= { f3L3QosPolicerThresholdEntry 1 }

f3L3QosPolicerThresholdInterval OBJECT-TYPE
    SYNTAX     CmPmIntervalType
    MAX-ACCESS read-only
    STATUS     current
    DESCRIPTION
        "The interval over which monitored value is
        sampled and compared with the specified threshold."
    ::= { f3L3QosPolicerThresholdEntry 2 }

f3L3QosPolicerThresholdVariable OBJECT-TYPE
    SYNTAX     VariablePointer
    MAX-ACCESS read-only
    STATUS     current
    DESCRIPTION
        "The object identifier of the particular variable to be
        sampled."
    ::= { f3L3QosPolicerThresholdEntry 3 }

f3L3QosPolicerThresholdValueLo OBJECT-TYPE
    SYNTAX     Unsigned32
    MAX-ACCESS read-write
    STATUS     current
    DESCRIPTION
        "Lower 32 bits of the threshold value."
    ::= { f3L3QosPolicerThresholdEntry 4 }

f3L3QosPolicerThresholdValueHi OBJECT-TYPE
    SYNTAX     Unsigned32
    MAX-ACCESS read-write
    STATUS     current
    DESCRIPTION
        "Higher 32 bits of the threshold value."
    ::= { f3L3QosPolicerThresholdEntry 5 }

f3L3QosPolicerThresholdMonValue OBJECT-TYPE
    SYNTAX     Counter64
    MAX-ACCESS read-only
    STATUS     current
    DESCRIPTION
        "Monitored value corresponding to f3L3QosPolicerThresholdVariable."
    ::= { f3L3QosPolicerThresholdEntry 6 }

--
-- L3 flow point Level Quality of Service(QOS) Shaper Current Statistics Table
--
f3L3QosShaperStatsTable OBJECT-TYPE
    SYNTAX      SEQUENCE OF F3L3QosShaperStatsEntry
    MAX-ACCESS  not-accessible
    STATUS      current
    DESCRIPTION
            "A collection of L3 flow point Level QOS Shaper statistics.  
             These reflect the current data."
    ::= { f3L3Performance 13 }

f3L3QosShaperStatsEntry OBJECT-TYPE
    SYNTAX      F3L3QosShaperStatsEntry 
    MAX-ACCESS  not-accessible
    STATUS      current
    DESCRIPTION
            "A conceptual row in the f3L3QosShaperStatsTable.
             Entries exist in this table for each QOS Shaper per L3 flow point."
    INDEX { neIndex, shelfIndex, slotIndex, f3L3FlowPointPortTypeIndex, 
            f3L3FlowPointPortIndex, f3L3FlowPointIndex,
            f3L3QosShaperIndex, f3L3QosShaperStatsIndex }
    ::= { f3L3QosShaperStatsTable 1 }

F3L3QosShaperStatsEntry ::= SEQUENCE {
    f3L3QosShaperStatsIndex             Integer32,
    f3L3QosShaperStatsIntervalType      CmPmIntervalType,
    f3L3QosShaperStatsValid             TruthValue,
    f3L3QosShaperStatsAction            CmPmBinAction,
    f3L3QosShaperStatsBT                PerfCounter64,
    f3L3QosShaperStatsBTD               PerfCounter64,
    f3L3QosShaperStatsFD                PerfCounter64,
    f3L3QosShaperStatsFTD               PerfCounter64,
    f3L3QosShaperStatsBR                PerfCounter64,
    f3L3QosShaperStatsFR                PerfCounter64,
    f3L3QosShaperStatsABRRL             PerfCounter64,
    f3L3QosShaperStatsABRRLR            PerfCounter64,
    f3L3QosShaperStatsBREDD             PerfCounter64,
    f3L3QosShaperStatsFREDD             PerfCounter64
}

f3L3QosShaperStatsIndex OBJECT-TYPE
    SYNTAX      Integer32 (1..65535)
    MAX-ACCESS  read-only
    STATUS      current
    DESCRIPTION
            "An arbitrary integer index value used to uniquely identify
            this QOS Shaper statistics entry.
            1 - 15min
            2 - 1day
            3 - rollover
            4 - 5min"
    ::= { f3L3QosShaperStatsEntry 1 }

f3L3QosShaperStatsIntervalType OBJECT-TYPE
    SYNTAX      CmPmIntervalType
    MAX-ACCESS  read-only
    STATUS      current
    DESCRIPTION
            "Interval over which Performance Monitoring data is collected."
    ::= { f3L3QosShaperStatsEntry 2 }

f3L3QosShaperStatsValid OBJECT-TYPE
    SYNTAX      TruthValue
    MAX-ACCESS  read-only
    STATUS      current
    DESCRIPTION
            "Indicates the validity of the bin."
    ::= { f3L3QosShaperStatsEntry 3 }

f3L3QosShaperStatsAction OBJECT-TYPE
    SYNTAX      CmPmBinAction
    MAX-ACCESS  read-write
    STATUS      current
    DESCRIPTION
            "Allows the Manager to clear the bin."
    ::= { f3L3QosShaperStatsEntry 4 }

f3L3QosShaperStatsBT OBJECT-TYPE
     SYNTAX     PerfCounter64
     MAX-ACCESS read-only
     STATUS     current
     DESCRIPTION
         "Bytes Transmitted."
     ::= { f3L3QosShaperStatsEntry 5 }

f3L3QosShaperStatsBTD OBJECT-TYPE
     SYNTAX     PerfCounter64
     MAX-ACCESS read-only
     STATUS     current
     DESCRIPTION
         "Bytes Tail Dropped."
     ::= { f3L3QosShaperStatsEntry 6 }

f3L3QosShaperStatsFD OBJECT-TYPE
     SYNTAX     PerfCounter64
     MAX-ACCESS read-only
     STATUS     current
     DESCRIPTION
         "Frames Dequeued."
     ::= { f3L3QosShaperStatsEntry 7 }

f3L3QosShaperStatsFTD OBJECT-TYPE
     SYNTAX     PerfCounter64
     MAX-ACCESS read-only
     STATUS     current
     DESCRIPTION
         "Frames Tail Dropped."
     ::= { f3L3QosShaperStatsEntry 8 }

f3L3QosShaperStatsBR OBJECT-TYPE
     SYNTAX     PerfCounter64
     MAX-ACCESS read-only
     STATUS     current
     DESCRIPTION
         "Bytes Replicated."
     ::= { f3L3QosShaperStatsEntry 9 }

f3L3QosShaperStatsFR OBJECT-TYPE
     SYNTAX     PerfCounter64
     MAX-ACCESS read-only
     STATUS     current
     DESCRIPTION
         "Frames Replicated."
     ::= { f3L3QosShaperStatsEntry 10 }

f3L3QosShaperStatsABRRL OBJECT-TYPE
     SYNTAX     PerfCounter64
     MAX-ACCESS read-only
     STATUS     current
     DESCRIPTION
         "Average Bit Rate - Rate Limited."
     ::= { f3L3QosShaperStatsEntry 11 }

f3L3QosShaperStatsABRRLR OBJECT-TYPE
     SYNTAX     PerfCounter64
     MAX-ACCESS read-only
     STATUS     current
     DESCRIPTION
         "Average Bit Rate - Rate Limited, Replicated."
     ::= { f3L3QosShaperStatsEntry 12 }

f3L3QosShaperStatsBREDD OBJECT-TYPE
     SYNTAX     PerfCounter64
     MAX-ACCESS read-only
     STATUS     current
     DESCRIPTION
         "Bytes Random Early Discard, Dropped."
     ::= { f3L3QosShaperStatsEntry 13 }

f3L3QosShaperStatsFREDD OBJECT-TYPE
     SYNTAX     PerfCounter64
     MAX-ACCESS read-only
     STATUS     current
     DESCRIPTION
         "Frames Random Early Discard, Dropped."
     ::= { f3L3QosShaperStatsEntry 14 }

--
-- Quality of Service(QOS) Shaper History Statistics Table
--
f3L3QosShaperHistoryTable OBJECT-TYPE
    SYNTAX      SEQUENCE OF F3L3QosShaperHistoryEntry
    MAX-ACCESS  not-accessible
    STATUS      current
    DESCRIPTION
            "A collection of l3 flow point Level QOS Shaper statistics.
             These reflect the history data."
    ::= { f3L3Performance 14 }

f3L3QosShaperHistoryEntry OBJECT-TYPE
    SYNTAX      F3L3QosShaperHistoryEntry 
    MAX-ACCESS  not-accessible
    STATUS      current
    DESCRIPTION
            "A conceptual row in the f3L3QosShaperHistoryTable.
             Entries exist in this table for each Shaper per l3 flow point."
    INDEX { neIndex, shelfIndex, slotIndex, f3L3FlowPointPortTypeIndex, 
            f3L3FlowPointPortIndex, f3L3FlowPointIndex,
            f3L3QosShaperIndex, f3L3QosShaperStatsIndex, f3L3QosShaperHistoryIndex }
    ::= { f3L3QosShaperHistoryTable 1 }

F3L3QosShaperHistoryEntry ::= SEQUENCE {
    f3L3QosShaperHistoryIndex             Integer32,
    f3L3QosShaperHistoryTime              DateAndTime,
    f3L3QosShaperHistoryValid             TruthValue,
    f3L3QosShaperHistoryAction            CmPmBinAction,
    f3L3QosShaperHistoryBT                PerfCounter64,
    f3L3QosShaperHistoryBTD               PerfCounter64,
    f3L3QosShaperHistoryFD                PerfCounter64,
    f3L3QosShaperHistoryFTD               PerfCounter64,
    f3L3QosShaperHistoryBR                PerfCounter64,
    f3L3QosShaperHistoryFR                PerfCounter64,
    f3L3QosShaperHistoryABRRL             PerfCounter64,
    f3L3QosShaperHistoryABRRLR            PerfCounter64,
    f3L3QosShaperHistoryBREDD             PerfCounter64,
    f3L3QosShaperHistoryFREDD             PerfCounter64
}

f3L3QosShaperHistoryIndex OBJECT-TYPE
    SYNTAX      Integer32 (1..65535)
    MAX-ACCESS  read-only
    STATUS      current
    DESCRIPTION
            "An arbitrary integer index value used to uniquely identify
            this QOS Shaper statistics entry."
    ::= { f3L3QosShaperHistoryEntry 1 }

f3L3QosShaperHistoryTime OBJECT-TYPE
    SYNTAX      DateAndTime
    MAX-ACCESS  read-only
    STATUS      current
    DESCRIPTION
            "Indicates the time of history bin creation." 
    ::= { f3L3QosShaperHistoryEntry 2 }

f3L3QosShaperHistoryValid OBJECT-TYPE
    SYNTAX      TruthValue
    MAX-ACCESS  read-only
    STATUS      current
    DESCRIPTION
            "Indicates the validity of the bin."
    ::= { f3L3QosShaperHistoryEntry 3 }

f3L3QosShaperHistoryAction OBJECT-TYPE
    SYNTAX      CmPmBinAction
    MAX-ACCESS  read-write
    STATUS      current
    DESCRIPTION
            "Allows the Manager to clear the bin."
    ::= { f3L3QosShaperHistoryEntry 4 }

f3L3QosShaperHistoryBT OBJECT-TYPE
     SYNTAX     PerfCounter64
     MAX-ACCESS read-only
     STATUS     current
     DESCRIPTION
         "Bytes Transmitted."
     ::= { f3L3QosShaperHistoryEntry 5 }

f3L3QosShaperHistoryBTD OBJECT-TYPE
     SYNTAX     PerfCounter64
     MAX-ACCESS read-only
     STATUS     current
     DESCRIPTION
         "Bytes Tail Dropped."
     ::= { f3L3QosShaperHistoryEntry 6 }

f3L3QosShaperHistoryFD OBJECT-TYPE
     SYNTAX     PerfCounter64
     MAX-ACCESS read-only
     STATUS     current
     DESCRIPTION
         "Frames Dequeued."
     ::= { f3L3QosShaperHistoryEntry 7 }

f3L3QosShaperHistoryFTD OBJECT-TYPE
     SYNTAX     PerfCounter64
     MAX-ACCESS read-only
     STATUS     current
     DESCRIPTION
         "Frames Tail Dropped."
     ::= { f3L3QosShaperHistoryEntry 8 }

f3L3QosShaperHistoryBR OBJECT-TYPE
     SYNTAX     PerfCounter64
     MAX-ACCESS read-only
     STATUS     current
     DESCRIPTION
         "Bytes Replicated."
     ::= { f3L3QosShaperHistoryEntry 9 }

f3L3QosShaperHistoryFR OBJECT-TYPE
     SYNTAX     PerfCounter64
     MAX-ACCESS read-only
     STATUS     current
     DESCRIPTION
         "Frames Replicated."
     ::= { f3L3QosShaperHistoryEntry 10 }

f3L3QosShaperHistoryABRRL OBJECT-TYPE
     SYNTAX     PerfCounter64
     MAX-ACCESS read-only
     STATUS     current
     DESCRIPTION
         "Average Bit Rate - Rate Limited."
     ::= { f3L3QosShaperHistoryEntry 11 }

f3L3QosShaperHistoryABRRLR OBJECT-TYPE
     SYNTAX     PerfCounter64
     MAX-ACCESS read-only
     STATUS     current
     DESCRIPTION
         "Average Bit Rate - Rate Limited, Replicated."
     ::= { f3L3QosShaperHistoryEntry 12 }

f3L3QosShaperHistoryBREDD OBJECT-TYPE
     SYNTAX     PerfCounter64
     MAX-ACCESS read-only
     STATUS     current
     DESCRIPTION
         "Bytes Random Early Discard, Dropped."
     ::= { f3L3QosShaperHistoryEntry 13 }

f3L3QosShaperHistoryFREDD OBJECT-TYPE
     SYNTAX     PerfCounter64
     MAX-ACCESS read-only
     STATUS     current
     DESCRIPTION
         "Frames Random Early Discard, Dropped."
     ::= { f3L3QosShaperHistoryEntry 14 }

--
-- L3 flow point QOS Shaper Threshold Table
--
f3L3QosShaperThresholdTable OBJECT-TYPE
    SYNTAX      SEQUENCE OF F3L3QosShaperThresholdEntry
    MAX-ACCESS  not-accessible
    STATUS      current
    DESCRIPTION
            "A table of entries that allow manageability of QOS
             Shaper Thresholds."
    ::= { f3L3Performance 15 }

f3L3QosShaperThresholdEntry OBJECT-TYPE
    SYNTAX      F3L3QosShaperThresholdEntry
    MAX-ACCESS  not-accessible
    STATUS      current
    DESCRIPTION
            "A conceptual row in the f3L3QosShaperThresholdTable."
    INDEX { neIndex, shelfIndex, slotIndex, f3L3FlowPointPortTypeIndex, 
            f3L3FlowPointPortIndex, f3L3FlowPointIndex,
            f3L3QosShaperIndex, f3L3QosShaperStatsIndex, 
            f3L3QosShaperThresholdIndex }
    ::= { f3L3QosShaperThresholdTable 1 }

F3L3QosShaperThresholdEntry ::= SEQUENCE {
    f3L3QosShaperThresholdIndex       Integer32,
    f3L3QosShaperThresholdInterval    CmPmIntervalType,
    f3L3QosShaperThresholdVariable    VariablePointer,
    f3L3QosShaperThresholdValueLo     Unsigned32,
    f3L3QosShaperThresholdValueHi     Unsigned32,
    f3L3QosShaperThresholdMonValue    Counter64
}

f3L3QosShaperThresholdIndex OBJECT-TYPE
    SYNTAX     Integer32 (1..65535)
    MAX-ACCESS read-only
    STATUS     current
    DESCRIPTION
        "An index that uniquely identifies an entry in the
        f3L3QosShaperThresholdTable."
    ::= { f3L3QosShaperThresholdEntry 1 }

f3L3QosShaperThresholdInterval OBJECT-TYPE
    SYNTAX     CmPmIntervalType
    MAX-ACCESS read-only
    STATUS     current
    DESCRIPTION
        "The interval over which monitored value is
        sampled and compared with the specified threshold."
    ::= { f3L3QosShaperThresholdEntry 2 }

f3L3QosShaperThresholdVariable OBJECT-TYPE
    SYNTAX     VariablePointer
    MAX-ACCESS read-only
    STATUS     current
    DESCRIPTION
        "The object identifier of the particular variable to be
        sampled."
    ::= { f3L3QosShaperThresholdEntry 3 }

f3L3QosShaperThresholdValueLo OBJECT-TYPE
    SYNTAX     Unsigned32
    MAX-ACCESS read-write
    STATUS     current
    DESCRIPTION
        "Lower 32 bits of the threshold value."
    ::= { f3L3QosShaperThresholdEntry 4 }

f3L3QosShaperThresholdValueHi OBJECT-TYPE
    SYNTAX     Unsigned32
    MAX-ACCESS read-write
    STATUS     current
    DESCRIPTION
        "Higher 32 bits of the threshold value."
    ::= { f3L3QosShaperThresholdEntry 5 }

f3L3QosShaperThresholdMonValue OBJECT-TYPE
    SYNTAX     Counter64
    MAX-ACCESS read-only
    STATUS     current
    DESCRIPTION
        "Monitored value corresponding to f3L3QosShaperThresholdVariable."
    ::= { f3L3QosShaperThresholdEntry 6 }


--
-- L3 A2N acl rule Current Statistics Table
--
f3L2A2NAclRuleStatsTable OBJECT-TYPE
    SYNTAX      SEQUENCE OF F3L2A2NAclRuleStatsEntry
    MAX-ACCESS  not-accessible
    STATUS      current
    DESCRIPTION
            "A collection of L3 acl rule related statistics.  
             These reflect the current data."
    ::= { f3L3Performance 16 }

f3L2A2NAclRuleStatsEntry OBJECT-TYPE
    SYNTAX      F3L2A2NAclRuleStatsEntry 
    MAX-ACCESS  not-accessible
    STATUS      current
    DESCRIPTION
            "A conceptual row in the f3L2A2NAclRuleStatsTable.
             Entries exist in this table for each Acl rule."
    INDEX { neIndex, shelfIndex, slotIndex,
            f3L3FlowPointPortIndex, f3L2A2NAclRuleParentIndex, f3L2A2NAclRuleIndex, f3L2A2NAclRuleStatsIndex }
    ::= { f3L2A2NAclRuleStatsTable 1 }

F3L2A2NAclRuleStatsEntry ::= SEQUENCE {
    f3L2A2NAclRuleStatsIndex               Integer32,
    f3L2A2NAclRuleStatsIntervalType        CmPmIntervalType,
    f3L2A2NAclRuleStatsValid               TruthValue,
    f3L2A2NAclRuleStatsAction              CmPmBinAction,
    f3L2A2NAclRuleStatsRuleMatch           PerfCounter64
}

f3L2A2NAclRuleStatsIndex OBJECT-TYPE
    SYNTAX      Integer32 (1..4)
    MAX-ACCESS  read-only
    STATUS      current
    DESCRIPTION
            "An arbitrary integer index value used to uniquely identify
            this L3 flow point statistics entry. 
            1 - 15min
            2 - 1day
            3 - rollover
            4 - 5min"
    ::= { f3L2A2NAclRuleStatsEntry 1 }

f3L2A2NAclRuleStatsIntervalType OBJECT-TYPE
    SYNTAX      CmPmIntervalType
    MAX-ACCESS  read-only
    STATUS      current
    DESCRIPTION
            "Interval over which Performance Monitoring data is collected."
    ::= { f3L2A2NAclRuleStatsEntry 2 }

f3L2A2NAclRuleStatsValid OBJECT-TYPE
    SYNTAX      TruthValue
    MAX-ACCESS  read-only
    STATUS      current
    DESCRIPTION
            "Indicates the validity of the bin."
    ::= { f3L2A2NAclRuleStatsEntry 3 }

f3L2A2NAclRuleStatsAction OBJECT-TYPE
    SYNTAX      CmPmBinAction
    MAX-ACCESS  read-write
    STATUS      current
    DESCRIPTION
            "Allows the Manager to clear the bin."
    ::= { f3L2A2NAclRuleStatsEntry 4 }

f3L2A2NAclRuleStatsRuleMatch OBJECT-TYPE
     SYNTAX     PerfCounter64
     MAX-ACCESS read-only
     STATUS     current
     DESCRIPTION
         "The number of packets matching the ACL rule."
     ::= { f3L2A2NAclRuleStatsEntry 5 }

--
-- L3 acl rule history Statistics Table
--
f3L2A2NAclRuleHistoryTable OBJECT-TYPE
    SYNTAX      SEQUENCE OF F3L2A2NAclRuleHistoryEntry
    MAX-ACCESS  not-accessible
    STATUS      current
    DESCRIPTION
            "A collection of L3 acl rule related history statistics.  
             These reflect the history data."
    ::= { f3L3Performance 17 }

f3L2A2NAclRuleHistoryEntry OBJECT-TYPE
    SYNTAX      F3L2A2NAclRuleHistoryEntry 
    MAX-ACCESS  not-accessible
    STATUS      current
    DESCRIPTION
            "A conceptual row in the f3L2A2NAclRuleHistoryTable.
             Entries exist in this table for each L3 acl rule."
    INDEX { neIndex, shelfIndex, slotIndex,
            f3L3FlowPointPortIndex, f3L2A2NAclRuleParentIndex, f3L2A2NAclRuleIndex,
            f3L2A2NAclRuleStatsIndex, f3L2A2NAclRuleHistoryIndex }
    ::= { f3L2A2NAclRuleHistoryTable 1 }

F3L2A2NAclRuleHistoryEntry ::= SEQUENCE {
    f3L2A2NAclRuleHistoryIndex               Integer32,
    f3L2A2NAclRuleHistoryTime                DateAndTime,
    f3L2A2NAclRuleHistoryValid               TruthValue,
    f3L2A2NAclRuleHistoryAction              CmPmBinAction,
    f3L2A2NAclRuleHistoryRuleMatch           PerfCounter64
}

f3L2A2NAclRuleHistoryIndex OBJECT-TYPE
    SYNTAX      Integer32 (1..65535)
    MAX-ACCESS  read-only
    STATUS      current
    DESCRIPTION
            "An arbitrary integer index value used to uniquely identify
            this L3 flow point statistics entry. 
            1 - 15min
            2 - 1day
            3 - rollover
            4 - 5min"
    ::= { f3L2A2NAclRuleHistoryEntry 1 }

f3L2A2NAclRuleHistoryTime OBJECT-TYPE
    SYNTAX      DateAndTime
    MAX-ACCESS  read-only
    STATUS      current
    DESCRIPTION
            "Indicates the time of history bin creation." 
    ::= { f3L2A2NAclRuleHistoryEntry 2 }

f3L2A2NAclRuleHistoryValid OBJECT-TYPE
    SYNTAX      TruthValue
    MAX-ACCESS  read-only
    STATUS      current
    DESCRIPTION
            "Indicates the validity of the bin."
    ::= { f3L2A2NAclRuleHistoryEntry 3 }

f3L2A2NAclRuleHistoryAction OBJECT-TYPE
    SYNTAX      CmPmBinAction
    MAX-ACCESS  read-write
    STATUS      current
    DESCRIPTION
            "Allows the Manager to clear the bin."
    ::= { f3L2A2NAclRuleHistoryEntry 4 }

f3L2A2NAclRuleHistoryRuleMatch OBJECT-TYPE
     SYNTAX     PerfCounter64
     MAX-ACCESS read-only
     STATUS     current
     DESCRIPTION
         "The number of packets matching acl rule."
     ::= { f3L2A2NAclRuleHistoryEntry 5 }

--
-- L3 acl rule Threshold Table
--
f3L2A2NAclRuleThresholdTable OBJECT-TYPE
    SYNTAX      SEQUENCE OF F3L2A2NAclRuleThresholdEntry
    MAX-ACCESS  not-accessible
    STATUS      current
    DESCRIPTION
            "A table of entries that allow manageability of L3 acl rule Thresholds."
    ::= { f3L3Performance 18 }

f3L2A2NAclRuleThresholdEntry OBJECT-TYPE
    SYNTAX      F3L2A2NAclRuleThresholdEntry
    MAX-ACCESS  not-accessible
    STATUS      current
    DESCRIPTION
            "A conceptual row in the f3L2A2NAclRuleThresholdTable."
    INDEX { neIndex, shelfIndex, slotIndex,
            f3L3FlowPointPortIndex, f3L2A2NAclRuleParentIndex, f3L2A2NAclRuleIndex,
            f3L2A2NAclRuleStatsIndex, f3L2A2NAclRuleThresholdIndex }
    ::= { f3L2A2NAclRuleThresholdTable 1 }

F3L2A2NAclRuleThresholdEntry ::= SEQUENCE {
    f3L2A2NAclRuleThresholdIndex       Integer32,
    f3L2A2NAclRuleThresholdInterval    CmPmIntervalType,
    f3L2A2NAclRuleThresholdVariable    VariablePointer,
    f3L2A2NAclRuleThresholdValueLo     Unsigned32,
    f3L2A2NAclRuleThresholdValueHi     Unsigned32,
    f3L2A2NAclRuleThresholdMonValue    Counter64
}

f3L2A2NAclRuleThresholdIndex OBJECT-TYPE
    SYNTAX     Integer32 (1..65535)
    MAX-ACCESS read-only
    STATUS     current
    DESCRIPTION
        "An index that uniquely identifies an entry in the
        f3L2A2NAclRuleThresholdTable."
    ::= { f3L2A2NAclRuleThresholdEntry 1 }

f3L2A2NAclRuleThresholdInterval OBJECT-TYPE
    SYNTAX     CmPmIntervalType
    MAX-ACCESS read-only
    STATUS     current
    DESCRIPTION
        "The interval over which monitored value is
        sampled and compared with the specified threshold."
    ::= { f3L2A2NAclRuleThresholdEntry 2 }

f3L2A2NAclRuleThresholdVariable OBJECT-TYPE
    SYNTAX     VariablePointer
    MAX-ACCESS read-only
    STATUS     current
    DESCRIPTION
        "The object identifier of the particular variable to be
        sampled."
    ::= { f3L2A2NAclRuleThresholdEntry 3 }

f3L2A2NAclRuleThresholdValueLo OBJECT-TYPE
    SYNTAX     Unsigned32
    MAX-ACCESS read-write
    STATUS     current
    DESCRIPTION
        "Lower 32 bits of the threshold value."
    ::= { f3L2A2NAclRuleThresholdEntry 4 }

f3L2A2NAclRuleThresholdValueHi OBJECT-TYPE
    SYNTAX     Unsigned32
    MAX-ACCESS read-write
    STATUS     current
    DESCRIPTION
        "Higher 32 bits of the threshold value."
    ::= { f3L2A2NAclRuleThresholdEntry 5 }

f3L2A2NAclRuleThresholdMonValue OBJECT-TYPE
    SYNTAX     Counter64
    MAX-ACCESS read-only
    STATUS     current
    DESCRIPTION
        "Monitored value corresponding to f3L2A2NAclRuleThresholdVariable."
    ::= { f3L2A2NAclRuleThresholdEntry 6 }


--
-- L3 N2A acl rule Current Statistics Table
--
f3L2N2AAclRuleStatsTable OBJECT-TYPE
    SYNTAX      SEQUENCE OF F3L2N2AAclRuleStatsEntry
    MAX-ACCESS  not-accessible
    STATUS      current
    DESCRIPTION
            "A collection of L3 acl rule related statistics.  
             These reflect the current data."
    ::= { f3L3Performance 19 }

f3L2N2AAclRuleStatsEntry OBJECT-TYPE
    SYNTAX      F3L2N2AAclRuleStatsEntry 
    MAX-ACCESS  not-accessible
    STATUS      current
    DESCRIPTION
            "A conceptual row in the f3L2N2AAclRuleStatsTable.
             Entries exist in this table for each Acl rule."
    INDEX { neIndex, shelfIndex, slotIndex,
            f3L3FlowPointPortIndex, f3L2N2AAclRuleParentIndex, f3L2N2AAclRuleIndex, f3L2N2AAclRuleStatsIndex }
    ::= { f3L2N2AAclRuleStatsTable 1 }

F3L2N2AAclRuleStatsEntry ::= SEQUENCE {
    f3L2N2AAclRuleStatsIndex               Integer32,
    f3L2N2AAclRuleStatsIntervalType        CmPmIntervalType,
    f3L2N2AAclRuleStatsValid               TruthValue,
    f3L2N2AAclRuleStatsAction              CmPmBinAction,
    f3L2N2AAclRuleStatsRuleMatch           PerfCounter64
}

f3L2N2AAclRuleStatsIndex OBJECT-TYPE
    SYNTAX      Integer32 (1..4)
    MAX-ACCESS  read-only
    STATUS      current
    DESCRIPTION
            "An arbitrary integer index value used to uniquely identify
            this L3 flow point statistics entry. 
            1 - 15min
            2 - 1day
            3 - rollover
            4 - 5min"
    ::= { f3L2N2AAclRuleStatsEntry 1 }

f3L2N2AAclRuleStatsIntervalType OBJECT-TYPE
    SYNTAX      CmPmIntervalType
    MAX-ACCESS  read-only
    STATUS      current
    DESCRIPTION
            "Interval over which Performance Monitoring data is collected."
    ::= { f3L2N2AAclRuleStatsEntry 2 }

f3L2N2AAclRuleStatsValid OBJECT-TYPE
    SYNTAX      TruthValue
    MAX-ACCESS  read-only
    STATUS      current
    DESCRIPTION
            "Indicates the validity of the bin."
    ::= { f3L2N2AAclRuleStatsEntry 3 }

f3L2N2AAclRuleStatsAction OBJECT-TYPE
    SYNTAX      CmPmBinAction
    MAX-ACCESS  read-write
    STATUS      current
    DESCRIPTION
            "Allows the Manager to clear the bin."
    ::= { f3L2N2AAclRuleStatsEntry 4 }

f3L2N2AAclRuleStatsRuleMatch OBJECT-TYPE
     SYNTAX     PerfCounter64
     MAX-ACCESS read-only
     STATUS     current
     DESCRIPTION
         "The number of packets matching the ACL rule."
     ::= { f3L2N2AAclRuleStatsEntry 5 }

--
-- L3 acl rule history Statistics Table
--
f3L2N2AAclRuleHistoryTable OBJECT-TYPE
    SYNTAX      SEQUENCE OF F3L2N2AAclRuleHistoryEntry
    MAX-ACCESS  not-accessible
    STATUS      current
    DESCRIPTION
            "A collection of L3 acl rule related history statistics.  
             These reflect the history data."
    ::= { f3L3Performance 20 }

f3L2N2AAclRuleHistoryEntry OBJECT-TYPE
    SYNTAX      F3L2N2AAclRuleHistoryEntry 
    MAX-ACCESS  not-accessible
    STATUS      current
    DESCRIPTION
            "A conceptual row in the f3L2N2AAclRuleHistoryTable.
             Entries exist in this table for each L3 acl rule."
    INDEX { neIndex, shelfIndex, slotIndex,
            f3L3FlowPointPortIndex, f3L2N2AAclRuleParentIndex, f3L2N2AAclRuleIndex,
            f3L2N2AAclRuleStatsIndex, f3L2N2AAclRuleHistoryIndex }
    ::= { f3L2N2AAclRuleHistoryTable 1 }

F3L2N2AAclRuleHistoryEntry ::= SEQUENCE {
    f3L2N2AAclRuleHistoryIndex               Integer32,
    f3L2N2AAclRuleHistoryTime                DateAndTime,
    f3L2N2AAclRuleHistoryValid               TruthValue,
    f3L2N2AAclRuleHistoryAction              CmPmBinAction,
    f3L2N2AAclRuleHistoryRuleMatch           PerfCounter64
}

f3L2N2AAclRuleHistoryIndex OBJECT-TYPE
    SYNTAX      Integer32 (1..65535)
    MAX-ACCESS  read-only
    STATUS      current
    DESCRIPTION
            "An arbitrary integer index value used to uniquely identify
            this L3 flow point statistics entry. 
            1 - 15min
            2 - 1day
            3 - rollover
            4 - 5min"
    ::= { f3L2N2AAclRuleHistoryEntry 1 }

f3L2N2AAclRuleHistoryTime OBJECT-TYPE
    SYNTAX      DateAndTime
    MAX-ACCESS  read-only
    STATUS      current
    DESCRIPTION
            "Indicates the time of history bin creation." 
    ::= { f3L2N2AAclRuleHistoryEntry 2 }

f3L2N2AAclRuleHistoryValid OBJECT-TYPE
    SYNTAX      TruthValue
    MAX-ACCESS  read-only
    STATUS      current
    DESCRIPTION
            "Indicates the validity of the bin."
    ::= { f3L2N2AAclRuleHistoryEntry 3 }

f3L2N2AAclRuleHistoryAction OBJECT-TYPE
    SYNTAX      CmPmBinAction
    MAX-ACCESS  read-write
    STATUS      current
    DESCRIPTION
            "Allows the Manager to clear the bin."
    ::= { f3L2N2AAclRuleHistoryEntry 4 }

f3L2N2AAclRuleHistoryRuleMatch OBJECT-TYPE
     SYNTAX     PerfCounter64
     MAX-ACCESS read-only
     STATUS     current
     DESCRIPTION
         "The number of packets matching acl rule."
     ::= { f3L2N2AAclRuleHistoryEntry 5 }

--
-- L3 acl rule Threshold Table
--
f3L2N2AAclRuleThresholdTable OBJECT-TYPE
    SYNTAX      SEQUENCE OF F3L2N2AAclRuleThresholdEntry
    MAX-ACCESS  not-accessible
    STATUS      current
    DESCRIPTION
            "A table of entries that allow manageability of L3 acl rule Thresholds."
    ::= { f3L3Performance 21 }

f3L2N2AAclRuleThresholdEntry OBJECT-TYPE
    SYNTAX      F3L2N2AAclRuleThresholdEntry
    MAX-ACCESS  not-accessible
    STATUS      current
    DESCRIPTION
            "A conceptual row in the f3L2N2AAclRuleThresholdTable."
    INDEX { neIndex, shelfIndex, slotIndex,
            f3L3FlowPointPortIndex, f3L2N2AAclRuleParentIndex, f3L2N2AAclRuleIndex,
            f3L2N2AAclRuleStatsIndex, f3L2N2AAclRuleThresholdIndex }
    ::= { f3L2N2AAclRuleThresholdTable 1 }

F3L2N2AAclRuleThresholdEntry ::= SEQUENCE {
    f3L2N2AAclRuleThresholdIndex       Integer32,
    f3L2N2AAclRuleThresholdInterval    CmPmIntervalType,
    f3L2N2AAclRuleThresholdVariable    VariablePointer,
    f3L2N2AAclRuleThresholdValueLo     Unsigned32,
    f3L2N2AAclRuleThresholdValueHi     Unsigned32,
    f3L2N2AAclRuleThresholdMonValue    Counter64
}

f3L2N2AAclRuleThresholdIndex OBJECT-TYPE
    SYNTAX     Integer32 (1..65535)
    MAX-ACCESS read-only
    STATUS     current
    DESCRIPTION
        "An index that uniquely identifies an entry in the
        f3L2N2AAclRuleThresholdTable."
    ::= { f3L2N2AAclRuleThresholdEntry 1 }

f3L2N2AAclRuleThresholdInterval OBJECT-TYPE
    SYNTAX     CmPmIntervalType
    MAX-ACCESS read-only
    STATUS     current
    DESCRIPTION
        "The interval over which monitored value is
        sampled and compared with the specified threshold."
    ::= { f3L2N2AAclRuleThresholdEntry 2 }

f3L2N2AAclRuleThresholdVariable OBJECT-TYPE
    SYNTAX     VariablePointer
    MAX-ACCESS read-only
    STATUS     current
    DESCRIPTION
        "The object identifier of the particular variable to be
        sampled."
    ::= { f3L2N2AAclRuleThresholdEntry 3 }

f3L2N2AAclRuleThresholdValueLo OBJECT-TYPE
    SYNTAX     Unsigned32
    MAX-ACCESS read-write
    STATUS     current
    DESCRIPTION
        "Lower 32 bits of the threshold value."
    ::= { f3L2N2AAclRuleThresholdEntry 4 }

f3L2N2AAclRuleThresholdValueHi OBJECT-TYPE
    SYNTAX     Unsigned32
    MAX-ACCESS read-write
    STATUS     current
    DESCRIPTION
        "Higher 32 bits of the threshold value."
    ::= { f3L2N2AAclRuleThresholdEntry 5 }

f3L2N2AAclRuleThresholdMonValue OBJECT-TYPE
    SYNTAX     Counter64
    MAX-ACCESS read-only
    STATUS     current
    DESCRIPTION
        "Monitored value corresponding to f3L2N2AAclRuleThresholdVariable."
    ::= { f3L2N2AAclRuleThresholdEntry 6 }



--
-- L3 traffic ipv6 interface Current Statistics Table
--
f3L3TrafficIPv6InterfaceStatsTable OBJECT-TYPE
    SYNTAX      SEQUENCE OF F3L3TrafficIPv6InterfaceStatsEntry
    MAX-ACCESS  not-accessible
    STATUS      current
    DESCRIPTION
            "A collection of L3 traffic ipv6 interface related statistics.  
             These reflect the current data."
    ::= { f3L3Performance 22 }

f3L3TrafficIPv6InterfaceStatsEntry OBJECT-TYPE
    SYNTAX      F3L3TrafficIPv6InterfaceStatsEntry 
    MAX-ACCESS  not-accessible
    STATUS      current
    DESCRIPTION
            "A conceptual row in the f3L3TrafficIPv6InterfaceStatsTable.
             Entries exist in this table for each L3 traffic ipv6 interface."
    INDEX { neIndex, shelfIndex, slotIndex,
            f3L3FlowPointPortIndex, f3L3FlowPointIndex, f3L3TrafficIPv6IfIndex, f3L3TrafficIPv6InterfaceStatsIndex }
    ::= { f3L3TrafficIPv6InterfaceStatsTable 1 }

F3L3TrafficIPv6InterfaceStatsEntry ::= SEQUENCE {
    f3L3TrafficIPv6InterfaceStatsIndex               Integer32,
    f3L3TrafficIPv6InterfaceStatsIntervalType        CmPmIntervalType,
    f3L3TrafficIPv6InterfaceStatsValid               TruthValue,
    f3L3TrafficIPv6InterfaceStatsAction              CmPmBinAction,
    f3L3TrafficIPv6InterfaceStatsDhcpV6Tx            PerfCounter64,
    f3L3TrafficIPv6InterfaceStatsDhcpV6Rx            PerfCounter64,
    f3L3TrafficIPv6InterfaceStatsIcmpV6WONdpTx       PerfCounter64,
    f3L3TrafficIPv6InterfaceStatsIcmpV6WONdpRx       PerfCounter64,
    f3L3TrafficIPv6InterfaceStatsNdpNSTx             PerfCounter64,
    f3L3TrafficIPv6InterfaceStatsNdpNSRx             PerfCounter64,
    f3L3TrafficIPv6InterfaceStatsNdpNATx             PerfCounter64,
    f3L3TrafficIPv6InterfaceStatsNdpNARx             PerfCounter64,
    f3L3TrafficIPv6InterfaceStatsNdpRATx             PerfCounter64,
    f3L3TrafficIPv6InterfaceStatsNdpRARx             PerfCounter64,
    f3L3TrafficIPv6InterfaceStatsNdpRSTx             PerfCounter64,
    f3L3TrafficIPv6InterfaceStatsNdpRSRx             PerfCounter64
}

f3L3TrafficIPv6InterfaceStatsIndex OBJECT-TYPE
    SYNTAX      Integer32 (1..4)
    MAX-ACCESS  read-only
    STATUS      current
    DESCRIPTION
            "An arbitrary integer index value used to uniquely identify
            this L3 Traffic IPv6 interface statistics entry. 
            1 - 15min
            2 - 1day
            3 - rollover
            4 - 5min"
    ::= { f3L3TrafficIPv6InterfaceStatsEntry 1 }

f3L3TrafficIPv6InterfaceStatsIntervalType OBJECT-TYPE
    SYNTAX      CmPmIntervalType
    MAX-ACCESS  read-only
    STATUS      current
    DESCRIPTION
            "Interval over which Performance Monitoring data is collected."
    ::= { f3L3TrafficIPv6InterfaceStatsEntry 2 }

f3L3TrafficIPv6InterfaceStatsValid OBJECT-TYPE
    SYNTAX      TruthValue
    MAX-ACCESS  read-only
    STATUS      current
    DESCRIPTION
            "Indicates the validity of the bin."
    ::= { f3L3TrafficIPv6InterfaceStatsEntry 3 }

f3L3TrafficIPv6InterfaceStatsAction OBJECT-TYPE
    SYNTAX      CmPmBinAction
    MAX-ACCESS  read-write
    STATUS      current
    DESCRIPTION
            "Allows the Manager to clear the bin."
    ::= { f3L3TrafficIPv6InterfaceStatsEntry 4 }

f3L3TrafficIPv6InterfaceStatsDhcpV6Tx OBJECT-TYPE
     SYNTAX     PerfCounter64
     MAX-ACCESS read-only
     STATUS     current
     DESCRIPTION
         "."
     ::= { f3L3TrafficIPv6InterfaceStatsEntry 5 }

f3L3TrafficIPv6InterfaceStatsDhcpV6Rx OBJECT-TYPE
     SYNTAX     PerfCounter64
     MAX-ACCESS read-only
     STATUS     current
     DESCRIPTION
         "."
     ::= { f3L3TrafficIPv6InterfaceStatsEntry 6 }

f3L3TrafficIPv6InterfaceStatsIcmpV6WONdpTx OBJECT-TYPE
     SYNTAX     PerfCounter64
     MAX-ACCESS read-only
     STATUS     current
     DESCRIPTION
         "."
     ::= { f3L3TrafficIPv6InterfaceStatsEntry 7 }

f3L3TrafficIPv6InterfaceStatsIcmpV6WONdpRx OBJECT-TYPE
     SYNTAX     PerfCounter64
     MAX-ACCESS read-only
     STATUS     current
     DESCRIPTION
         "."
     ::= { f3L3TrafficIPv6InterfaceStatsEntry 8 }

f3L3TrafficIPv6InterfaceStatsNdpNSTx OBJECT-TYPE
     SYNTAX     PerfCounter64
     MAX-ACCESS read-only
     STATUS     current
     DESCRIPTION
         "."
     ::= { f3L3TrafficIPv6InterfaceStatsEntry 9 }

f3L3TrafficIPv6InterfaceStatsNdpNSRx OBJECT-TYPE
     SYNTAX     PerfCounter64
     MAX-ACCESS read-only
     STATUS     current
     DESCRIPTION
         "."
     ::= { f3L3TrafficIPv6InterfaceStatsEntry 10 }

f3L3TrafficIPv6InterfaceStatsNdpNATx OBJECT-TYPE
     SYNTAX     PerfCounter64
     MAX-ACCESS read-only
     STATUS     current
     DESCRIPTION
         "."
     ::= { f3L3TrafficIPv6InterfaceStatsEntry 11 }

f3L3TrafficIPv6InterfaceStatsNdpNARx OBJECT-TYPE
     SYNTAX     PerfCounter64
     MAX-ACCESS read-only
     STATUS     current
     DESCRIPTION
         "."
     ::= { f3L3TrafficIPv6InterfaceStatsEntry 12 }

f3L3TrafficIPv6InterfaceStatsNdpRATx OBJECT-TYPE
     SYNTAX     PerfCounter64
     MAX-ACCESS read-only
     STATUS     current
     DESCRIPTION
         "."
     ::= { f3L3TrafficIPv6InterfaceStatsEntry 13 }

f3L3TrafficIPv6InterfaceStatsNdpRARx OBJECT-TYPE
     SYNTAX     PerfCounter64
     MAX-ACCESS read-only
     STATUS     current
     DESCRIPTION
         "."
     ::= { f3L3TrafficIPv6InterfaceStatsEntry 14 }

f3L3TrafficIPv6InterfaceStatsNdpRSTx OBJECT-TYPE
     SYNTAX     PerfCounter64
     MAX-ACCESS read-only
     STATUS     current
     DESCRIPTION
         "."
     ::= { f3L3TrafficIPv6InterfaceStatsEntry 15 }

f3L3TrafficIPv6InterfaceStatsNdpRSRx OBJECT-TYPE
     SYNTAX     PerfCounter64
     MAX-ACCESS read-only
     STATUS     current
     DESCRIPTION
         "."
     ::= { f3L3TrafficIPv6InterfaceStatsEntry 16 }


--
-- L3 traffic ipv6 interface History Statistics Table
--
f3L3TrafficIPv6InterfaceHistoryTable OBJECT-TYPE
    SYNTAX      SEQUENCE OF F3L3TrafficIPv6InterfaceHistoryEntry
    MAX-ACCESS  not-accessible
    STATUS      current
    DESCRIPTION
            "A collection of L3 traffic ipv6 interface related statistics.  
             These reflect the current data."
    ::= { f3L3Performance 23 }

f3L3TrafficIPv6InterfaceHistoryEntry OBJECT-TYPE
    SYNTAX      F3L3TrafficIPv6InterfaceHistoryEntry 
    MAX-ACCESS  not-accessible
    STATUS      current
    DESCRIPTION
            "A conceptual row in the f3L3TrafficIPv6InterfaceHistoryTable.
             Entries exist in this table for each L3 traffic ipv6 interface."
    INDEX { neIndex, shelfIndex, slotIndex,
            f3L3FlowPointPortIndex, f3L3FlowPointIndex, 
            f3L3TrafficIPv6IfIndex, f3L3TrafficIPv6InterfaceStatsIndex,
            f3L3TrafficIPv6InterfaceHistoryIndex }
    ::= { f3L3TrafficIPv6InterfaceHistoryTable 1 }

F3L3TrafficIPv6InterfaceHistoryEntry ::= SEQUENCE {
    f3L3TrafficIPv6InterfaceHistoryIndex               Integer32,
    f3L3TrafficIPv6InterfaceHistoryTime                DateAndTime,
    f3L3TrafficIPv6InterfaceHistoryValid               TruthValue,
    f3L3TrafficIPv6InterfaceHistoryAction              CmPmBinAction,
    f3L3TrafficIPv6InterfaceHistoryDhcpV6Tx            PerfCounter64,
    f3L3TrafficIPv6InterfaceHistoryDhcpV6Rx            PerfCounter64,
    f3L3TrafficIPv6InterfaceHistoryIcmpV6WONdpTx       PerfCounter64,
    f3L3TrafficIPv6InterfaceHistoryIcmpV6WONdpRx       PerfCounter64,
    f3L3TrafficIPv6InterfaceHistoryNdpNSTx             PerfCounter64,
    f3L3TrafficIPv6InterfaceHistoryNdpNSRx             PerfCounter64,
    f3L3TrafficIPv6InterfaceHistoryNdpNATx             PerfCounter64,
    f3L3TrafficIPv6InterfaceHistoryNdpNARx             PerfCounter64,
    f3L3TrafficIPv6InterfaceHistoryNdpRATx             PerfCounter64,
    f3L3TrafficIPv6InterfaceHistoryNdpRARx             PerfCounter64,
    f3L3TrafficIPv6InterfaceHistoryNdpRSTx             PerfCounter64,
    f3L3TrafficIPv6InterfaceHistoryNdpRSRx             PerfCounter64
}

f3L3TrafficIPv6InterfaceHistoryIndex OBJECT-TYPE
    SYNTAX      Integer32 (1..4)
    MAX-ACCESS  read-only
    STATUS      current
    DESCRIPTION
            "An arbitrary integer index value used to uniquely identify
            this L3 Traffic IPv6 interface statistics entry. 
            1 - 15min
            2 - 1day
            3 - rollover
            4 - 5min"
    ::= { f3L3TrafficIPv6InterfaceHistoryEntry 1 }

f3L3TrafficIPv6InterfaceHistoryTime OBJECT-TYPE
    SYNTAX      DateAndTime
    MAX-ACCESS  read-only
    STATUS      current
    DESCRIPTION
            "Indicates the time of history bin creation." 
    ::= { f3L3TrafficIPv6InterfaceHistoryEntry 2 }

f3L3TrafficIPv6InterfaceHistoryValid OBJECT-TYPE
    SYNTAX      TruthValue
    MAX-ACCESS  read-only
    STATUS      current
    DESCRIPTION
            "Indicates the validity of the bin."
    ::= { f3L3TrafficIPv6InterfaceHistoryEntry 3 }

f3L3TrafficIPv6InterfaceHistoryAction OBJECT-TYPE
    SYNTAX      CmPmBinAction
    MAX-ACCESS  read-write
    STATUS      current
    DESCRIPTION
            "Allows the Manager to clear the bin."
    ::= { f3L3TrafficIPv6InterfaceHistoryEntry 4 }

f3L3TrafficIPv6InterfaceHistoryDhcpV6Tx OBJECT-TYPE
     SYNTAX     PerfCounter64
     MAX-ACCESS read-only
     STATUS     current
     DESCRIPTION
         "."
     ::= { f3L3TrafficIPv6InterfaceHistoryEntry 5 }

f3L3TrafficIPv6InterfaceHistoryDhcpV6Rx OBJECT-TYPE
     SYNTAX     PerfCounter64
     MAX-ACCESS read-only
     STATUS     current
     DESCRIPTION
         "."
     ::= { f3L3TrafficIPv6InterfaceHistoryEntry 6 }

f3L3TrafficIPv6InterfaceHistoryIcmpV6WONdpTx OBJECT-TYPE
     SYNTAX     PerfCounter64
     MAX-ACCESS read-only
     STATUS     current
     DESCRIPTION
         "."
     ::= { f3L3TrafficIPv6InterfaceHistoryEntry 7 }

f3L3TrafficIPv6InterfaceHistoryIcmpV6WONdpRx OBJECT-TYPE
     SYNTAX     PerfCounter64
     MAX-ACCESS read-only
     STATUS     current
     DESCRIPTION
         "."
     ::= { f3L3TrafficIPv6InterfaceHistoryEntry 8 }

f3L3TrafficIPv6InterfaceHistoryNdpNSTx OBJECT-TYPE
     SYNTAX     PerfCounter64
     MAX-ACCESS read-only
     STATUS     current
     DESCRIPTION
         "."
     ::= { f3L3TrafficIPv6InterfaceHistoryEntry 9 }

f3L3TrafficIPv6InterfaceHistoryNdpNSRx OBJECT-TYPE
     SYNTAX     PerfCounter64
     MAX-ACCESS read-only
     STATUS     current
     DESCRIPTION
         "."
     ::= { f3L3TrafficIPv6InterfaceHistoryEntry 10 }

f3L3TrafficIPv6InterfaceHistoryNdpNATx OBJECT-TYPE
     SYNTAX     PerfCounter64
     MAX-ACCESS read-only
     STATUS     current
     DESCRIPTION
         "."
     ::= { f3L3TrafficIPv6InterfaceHistoryEntry 11 }

f3L3TrafficIPv6InterfaceHistoryNdpNARx OBJECT-TYPE
     SYNTAX     PerfCounter64
     MAX-ACCESS read-only
     STATUS     current
     DESCRIPTION
         "."
     ::= { f3L3TrafficIPv6InterfaceHistoryEntry 12 }

f3L3TrafficIPv6InterfaceHistoryNdpRATx OBJECT-TYPE
     SYNTAX     PerfCounter64
     MAX-ACCESS read-only
     STATUS     current
     DESCRIPTION
         "."
     ::= { f3L3TrafficIPv6InterfaceHistoryEntry 13 }

f3L3TrafficIPv6InterfaceHistoryNdpRARx OBJECT-TYPE
     SYNTAX     PerfCounter64
     MAX-ACCESS read-only
     STATUS     current
     DESCRIPTION
         "."
     ::= { f3L3TrafficIPv6InterfaceHistoryEntry 14 }

f3L3TrafficIPv6InterfaceHistoryNdpRSTx OBJECT-TYPE
     SYNTAX     PerfCounter64
     MAX-ACCESS read-only
     STATUS     current
     DESCRIPTION
         "."
     ::= { f3L3TrafficIPv6InterfaceHistoryEntry 15 }

f3L3TrafficIPv6InterfaceHistoryNdpRSRx OBJECT-TYPE
     SYNTAX     PerfCounter64
     MAX-ACCESS read-only
     STATUS     current
     DESCRIPTION
         "."
     ::= { f3L3TrafficIPv6InterfaceHistoryEntry 16 }


--
-- L3 traffic ipv6 interface Threshold Table
--
f3L3TrafficIPv6InterfaceThresholdTable OBJECT-TYPE
    SYNTAX      SEQUENCE OF F3L3TrafficIPv6InterfaceThresholdEntry
    MAX-ACCESS  not-accessible
    STATUS      current
    DESCRIPTION
            "A table of entries that allow manageability of L3 traffic ipv6 interface Thresholds."
    ::= { f3L3Performance 24 }

f3L3TrafficIPv6InterfaceThresholdEntry OBJECT-TYPE
    SYNTAX      F3L3TrafficIPv6InterfaceThresholdEntry
    MAX-ACCESS  not-accessible
    STATUS      current
    DESCRIPTION
            "A conceptual row in the f3L3TrafficIPv6InterfaceThresholdTable."
    INDEX { neIndex, shelfIndex, slotIndex, 
            f3L3FlowPointPortIndex, f3L3FlowPointIndex, f3L3TrafficIPv6IfIndex,
            f3L3TrafficIPv6InterfaceStatsIndex, f3L3TrafficIPv6InterfaceThresholdIndex }
    ::= { f3L3TrafficIPv6InterfaceThresholdTable 1 }

F3L3TrafficIPv6InterfaceThresholdEntry ::= SEQUENCE {
    f3L3TrafficIPv6InterfaceThresholdIndex       Integer32,
    f3L3TrafficIPv6InterfaceThresholdInterval    CmPmIntervalType,
    f3L3TrafficIPv6InterfaceThresholdVariable    VariablePointer,
    f3L3TrafficIPv6InterfaceThresholdValueLo     Unsigned32,
    f3L3TrafficIPv6InterfaceThresholdValueHi     Unsigned32,
    f3L3TrafficIPv6InterfaceThresholdMonValue    Counter64
}

f3L3TrafficIPv6InterfaceThresholdIndex OBJECT-TYPE
    SYNTAX     Integer32 (1..65535)
    MAX-ACCESS read-only
    STATUS     current
    DESCRIPTION
        "An index that uniquely identifies an entry in the
        f3L3TrafficIPv6InterfaceThresholdTable."
    ::= { f3L3TrafficIPv6InterfaceThresholdEntry 1 }

f3L3TrafficIPv6InterfaceThresholdInterval OBJECT-TYPE
    SYNTAX     CmPmIntervalType
    MAX-ACCESS read-only
    STATUS     current
    DESCRIPTION
        "The interval over which monitored value is
        sampled and compared with the specified threshold."
    ::= { f3L3TrafficIPv6InterfaceThresholdEntry 2 }

f3L3TrafficIPv6InterfaceThresholdVariable OBJECT-TYPE
    SYNTAX     VariablePointer
    MAX-ACCESS read-only
    STATUS     current
    DESCRIPTION
        "The object identifier of the particular variable to be
        sampled."
    ::= { f3L3TrafficIPv6InterfaceThresholdEntry 3 }

f3L3TrafficIPv6InterfaceThresholdValueLo OBJECT-TYPE
    SYNTAX     Unsigned32
    MAX-ACCESS read-write
    STATUS     current
    DESCRIPTION
        "Lower 32 bits of the threshold value."
    ::= { f3L3TrafficIPv6InterfaceThresholdEntry 4 }

f3L3TrafficIPv6InterfaceThresholdValueHi OBJECT-TYPE
    SYNTAX     Unsigned32
    MAX-ACCESS read-write
    STATUS     current
    DESCRIPTION
        "Higher 32 bits of the threshold value."
    ::= { f3L3TrafficIPv6InterfaceThresholdEntry 5 }

f3L3TrafficIPv6InterfaceThresholdMonValue OBJECT-TYPE
    SYNTAX     Counter64
    MAX-ACCESS read-only
    STATUS     current
    DESCRIPTION
        "Monitored value corresponding to f3L3TrafficIPv6InterfaceThresholdVariable."
    ::= { f3L3TrafficIPv6InterfaceThresholdEntry 6 }

--
-- L3 flow point Current Statistics Table
--
cmL3FlowPointStatsTable OBJECT-TYPE
    SYNTAX      SEQUENCE OF CML3FlowPointStatsEntry
    MAX-ACCESS  not-accessible
    STATUS      current
    DESCRIPTION
            "A collection of L3 Flow Point related statistics.  
             These reflect the current data."
    ::= { f3L3Performance 25 }

cmL3FlowPointStatsEntry OBJECT-TYPE
    SYNTAX      CML3FlowPointStatsEntry 
    MAX-ACCESS  not-accessible
    STATUS      current
    DESCRIPTION
            "A conceptual row in the cmL3FlowPointStatsTable.
             Entries exist in this table for each L3 flow point."
    INDEX { neIndex, shelfIndex, slotIndex, 
            cmL3FlowPointPortIndex, cmL3FlowPointIndex, cmL3FlowPointStatsIndex }
    ::= { cmL3FlowPointStatsTable 1 }

CML3FlowPointStatsEntry ::= SEQUENCE {
    cmL3FlowPointStatsIndex               Integer32,
    cmL3FlowPointStatsIntervalType        CmPmIntervalType,
    cmL3FlowPointStatsValid               TruthValue,
    cmL3FlowPointStatsAction              CmPmBinAction,
    cmL3FlowPointStatsFMG                 PerfCounter64,
    cmL3FlowPointStatsFMY                 PerfCounter64,
    cmL3FlowPointStatsFMRD                PerfCounter64,
    cmL3FlowPointStatsFTD                 PerfCounter64,
    cmL3FlowPointStatsFragmentedDropAcl   PerfCounter64,
    cmL3FlowPointStatsAclRuleDrop         PerfCounter64,
    cmL3FlowPointStatsTtlEqual1Drop       PerfCounter64,
    cmL3FlowPointStatsFrameTx             PerfCounter64,
    cmL3FlowPointStatsFrameRx             PerfCounter64,
    cmL3FlowPointStatsNoRouteDrop         PerfCounter64,
    cmL3FlowPointStatsAclDropNoMatch      PerfCounter64
}

cmL3FlowPointStatsIndex OBJECT-TYPE
    SYNTAX      Integer32 (1..4)
    MAX-ACCESS  read-only
    STATUS      current
    DESCRIPTION
            "An arbitrary integer index value used to uniquely identify
            this L3 flow point statistics entry. 
            1 - 15min
            2 - 1day
            3 - rollover
            4 - 5min"
    ::= { cmL3FlowPointStatsEntry 1 }

cmL3FlowPointStatsIntervalType OBJECT-TYPE
    SYNTAX      CmPmIntervalType
    MAX-ACCESS  read-only
    STATUS      current
    DESCRIPTION
            "Interval over which Performance Monitoring data is collected."
    ::= { cmL3FlowPointStatsEntry 2 }

cmL3FlowPointStatsValid OBJECT-TYPE
    SYNTAX      TruthValue
    MAX-ACCESS  read-only
    STATUS      current
    DESCRIPTION
            "Indicates the validity of the bin."
    ::= { cmL3FlowPointStatsEntry 3 }

cmL3FlowPointStatsAction OBJECT-TYPE
    SYNTAX      CmPmBinAction
    MAX-ACCESS  read-write
    STATUS      current
    DESCRIPTION
            "Allows the Manager to clear the bin."
    ::= { cmL3FlowPointStatsEntry 4 }

cmL3FlowPointStatsFMG OBJECT-TYPE
     SYNTAX     PerfCounter64
     MAX-ACCESS read-only
     STATUS     current
     DESCRIPTION
         "The number of Frames Marked Green."
     ::= { cmL3FlowPointStatsEntry 5 }

cmL3FlowPointStatsFMY OBJECT-TYPE
     SYNTAX     PerfCounter64
     MAX-ACCESS read-only
     STATUS     current
     DESCRIPTION
         "The number of Frames Marked Yellow."
     ::= { cmL3FlowPointStatsEntry 6 }

cmL3FlowPointStatsFMRD OBJECT-TYPE
     SYNTAX     PerfCounter64
     MAX-ACCESS read-only
     STATUS     current
     DESCRIPTION
         "The number of Frames Marked Red and Discarded."
     ::= { cmL3FlowPointStatsEntry 7 }

cmL3FlowPointStatsFTD OBJECT-TYPE
     SYNTAX     PerfCounter64
     MAX-ACCESS read-only
     STATUS     current
     DESCRIPTION
         "The number of Frames Tail Dropped."
     ::= { cmL3FlowPointStatsEntry 8 }

cmL3FlowPointStatsFragmentedDropAcl OBJECT-TYPE
     SYNTAX     PerfCounter64
     MAX-ACCESS read-only
     STATUS     current
     DESCRIPTION
         "The number of dropped fragmented packets."
     ::= { cmL3FlowPointStatsEntry 9 }

cmL3FlowPointStatsAclRuleDrop OBJECT-TYPE
     SYNTAX     PerfCounter64
     MAX-ACCESS read-only
     STATUS     current
     DESCRIPTION
         "The number of dropped packets due to ACL rule."
     ::= { cmL3FlowPointStatsEntry 10 }

cmL3FlowPointStatsTtlEqual1Drop OBJECT-TYPE
     SYNTAX     PerfCounter64
     MAX-ACCESS read-only
     STATUS     current
     DESCRIPTION
         " the number of dropped packets due to ttl's value is 1."
     ::= { cmL3FlowPointStatsEntry 11 }

cmL3FlowPointStatsFrameTx OBJECT-TYPE
     SYNTAX     PerfCounter64
     MAX-ACCESS read-only
     STATUS     current
     DESCRIPTION
         "The number of total transmitted frames."
     ::= { cmL3FlowPointStatsEntry 12 }

cmL3FlowPointStatsFrameRx OBJECT-TYPE
     SYNTAX     PerfCounter64
     MAX-ACCESS read-only
     STATUS     current
     DESCRIPTION
         " The number of total received frames."
     ::= { cmL3FlowPointStatsEntry 13 }

cmL3FlowPointStatsNoRouteDrop OBJECT-TYPE
     SYNTAX     PerfCounter64
     MAX-ACCESS read-only
     STATUS     current
     DESCRIPTION
         " The number of frames drop due to no route."
     ::= { cmL3FlowPointStatsEntry 14 }

cmL3FlowPointStatsAclDropNoMatch OBJECT-TYPE
     SYNTAX     PerfCounter64
     MAX-ACCESS read-only
     STATUS     current
     DESCRIPTION
         "The number of dropped packets due to no match in ACL rule."
     ::= { cmL3FlowPointStatsEntry 15 }

--
-- CM L3 flow point history Statistics Table
--
cmL3FlowPointHistoryTable OBJECT-TYPE
    SYNTAX      SEQUENCE OF CML3FlowPointHistoryEntry
    MAX-ACCESS  not-accessible
    STATUS      current
    DESCRIPTION
            "A collection of L3 Flow Point related statistics.  
             These reflect the current data."
    ::= { f3L3Performance 26 }

cmL3FlowPointHistoryEntry OBJECT-TYPE
    SYNTAX      CML3FlowPointHistoryEntry 
    MAX-ACCESS  not-accessible
    STATUS      current
    DESCRIPTION
            "A conceptual row in the cmL3FlowPointHistoryTable.
             Entries exist in this table for each L3 flow point."
    INDEX { neIndex, shelfIndex, slotIndex, 
            cmL3FlowPointPortIndex, cmL3FlowPointIndex, cmL3FlowPointStatsIndex, cmL3FlowPointHistoryIndex }
    ::= { cmL3FlowPointHistoryTable 1 }

CML3FlowPointHistoryEntry ::= SEQUENCE {
    cmL3FlowPointHistoryIndex               Integer32,
    cmL3FlowPointHistoryTime                DateAndTime,
    cmL3FlowPointHistoryValid               TruthValue,
    cmL3FlowPointHistoryAction              CmPmBinAction,
    cmL3FlowPointHistoryFMG                 PerfCounter64,
    cmL3FlowPointHistoryFMY                 PerfCounter64,
    cmL3FlowPointHistoryFMRD                PerfCounter64,
    cmL3FlowPointHistoryFTD                 PerfCounter64,
    cmL3FlowPointHistoryFragmentedDropAcl   PerfCounter64,
    cmL3FlowPointHistoryAclRuleDrop         PerfCounter64,
    cmL3FlowPointHistoryTtlEqual1Drop       PerfCounter64,
    cmL3FlowPointHistoryFrameTx             PerfCounter64,
    cmL3FlowPointHistoryFrameRx             PerfCounter64,
    cmL3FlowPointHistoryNoRouteDrop         PerfCounter64,
    cmL3FlowPointHistoryAclDropNoMatch      PerfCounter64
}

cmL3FlowPointHistoryIndex OBJECT-TYPE
    SYNTAX      Integer32 (1..65535)
    MAX-ACCESS  read-only
    STATUS      current
    DESCRIPTION
           "An arbitrary integer index value used to uniquely identify
            the history bin."

    ::= { cmL3FlowPointHistoryEntry 1 }

cmL3FlowPointHistoryTime OBJECT-TYPE
    SYNTAX      DateAndTime
    MAX-ACCESS  read-only
    STATUS      current
    DESCRIPTION
            "Indicates the time of history bin creation." 
    ::= { cmL3FlowPointHistoryEntry 2 }

cmL3FlowPointHistoryValid OBJECT-TYPE
    SYNTAX      TruthValue
    MAX-ACCESS  read-only
    STATUS      current
    DESCRIPTION
            "Indicates the validity of the bin."
    ::= { cmL3FlowPointHistoryEntry 3 }

cmL3FlowPointHistoryAction OBJECT-TYPE
    SYNTAX      CmPmBinAction
    MAX-ACCESS  read-write
    STATUS      current
    DESCRIPTION
            "Allows the Manager to clear the bin."
    ::= { cmL3FlowPointHistoryEntry 4 }

cmL3FlowPointHistoryFMG OBJECT-TYPE
     SYNTAX     PerfCounter64
     MAX-ACCESS read-only
     STATUS     current
     DESCRIPTION
         "The number of Frames Marked Green."
     ::= { cmL3FlowPointHistoryEntry 5 }

cmL3FlowPointHistoryFMY OBJECT-TYPE
     SYNTAX     PerfCounter64
     MAX-ACCESS read-only
     STATUS     current
     DESCRIPTION
         "The number of Frames Marked Yellow."
     ::= { cmL3FlowPointHistoryEntry 6 }

cmL3FlowPointHistoryFMRD OBJECT-TYPE
     SYNTAX     PerfCounter64
     MAX-ACCESS read-only
     STATUS     current
     DESCRIPTION
         "The number of Frames Marked Red and Discarded."
     ::= { cmL3FlowPointHistoryEntry 7 }

cmL3FlowPointHistoryFTD OBJECT-TYPE
     SYNTAX     PerfCounter64
     MAX-ACCESS read-only
     STATUS     current
     DESCRIPTION
         "The number of Frames Tail Dropped."
     ::= { cmL3FlowPointHistoryEntry 8 }

cmL3FlowPointHistoryFragmentedDropAcl OBJECT-TYPE
     SYNTAX     PerfCounter64
     MAX-ACCESS read-only
     STATUS     current
     DESCRIPTION
         "The number of dropped fragmented packets."
     ::= { cmL3FlowPointHistoryEntry 9 }

cmL3FlowPointHistoryAclRuleDrop OBJECT-TYPE
     SYNTAX     PerfCounter64
     MAX-ACCESS read-only
     STATUS     current
     DESCRIPTION
         "The number of dropped packets due to ACL rule."
     ::= { cmL3FlowPointHistoryEntry 10 }

cmL3FlowPointHistoryTtlEqual1Drop OBJECT-TYPE
     SYNTAX     PerfCounter64
     MAX-ACCESS read-only
     STATUS     current
     DESCRIPTION
         " the number of dropped packets due to ttl's value is 1."
     ::= { cmL3FlowPointHistoryEntry 11 }

cmL3FlowPointHistoryFrameTx OBJECT-TYPE
     SYNTAX     PerfCounter64
     MAX-ACCESS read-only
     STATUS     current
     DESCRIPTION
         "The number of total transmitted frames."
     ::= { cmL3FlowPointHistoryEntry 12 }

cmL3FlowPointHistoryFrameRx OBJECT-TYPE
     SYNTAX     PerfCounter64
     MAX-ACCESS read-only
     STATUS     current
     DESCRIPTION
         " the number of total recieved frames."
     ::= { cmL3FlowPointHistoryEntry 13 }

cmL3FlowPointHistoryNoRouteDrop OBJECT-TYPE
     SYNTAX     PerfCounter64
     MAX-ACCESS read-only
     STATUS     current
     DESCRIPTION
         " the number of frames dropped due to no route."
     ::= { cmL3FlowPointHistoryEntry 14 }

cmL3FlowPointHistoryAclDropNoMatch OBJECT-TYPE
     SYNTAX     PerfCounter64
     MAX-ACCESS read-only
     STATUS     current
     DESCRIPTION
         "The number of dropped packets due to no match in ACL rule."
     ::= { cmL3FlowPointHistoryEntry 15 }

--
-- CM L3 Flow Point Threshold Table
--
cmL3FlowPointThresholdTable OBJECT-TYPE
    SYNTAX      SEQUENCE OF CML3FlowPointThresholdEntry
    MAX-ACCESS  not-accessible
    STATUS      current
    DESCRIPTION
            "A table of entries that allow manageability of L3 Flow Point Thresholds."
    ::= { f3L3Performance 27 }

cmL3FlowPointThresholdEntry OBJECT-TYPE
    SYNTAX      CML3FlowPointThresholdEntry
    MAX-ACCESS  not-accessible
    STATUS      current
    DESCRIPTION
            "A conceptual row in the cmL3FlowPointThresholdTable."
    INDEX { neIndex, shelfIndex, slotIndex, 
            cmL3FlowPointPortIndex, cmL3FlowPointIndex, cmL3FlowPointStatsIndex, cmL3FlowPointThresholdIndex }
    ::= { cmL3FlowPointThresholdTable 1 }

CML3FlowPointThresholdEntry ::= SEQUENCE {
    cmL3FlowPointThresholdIndex       Integer32,
    cmL3FlowPointThresholdInterval    CmPmIntervalType,
    cmL3FlowPointThresholdVariable    VariablePointer,
    cmL3FlowPointThresholdValueLo     Unsigned32,
    cmL3FlowPointThresholdValueHi     Unsigned32,
    cmL3FlowPointThresholdMonValue    Counter64
}

cmL3FlowPointThresholdIndex OBJECT-TYPE
    SYNTAX     Integer32 (1..65535)
    MAX-ACCESS read-only
    STATUS     current
    DESCRIPTION
        "An index that uniquely identifies an entry in the
        cmL3FlowPointThresholdTable."
    ::= { cmL3FlowPointThresholdEntry 1 }

cmL3FlowPointThresholdInterval OBJECT-TYPE
    SYNTAX     CmPmIntervalType
    MAX-ACCESS read-only
    STATUS     current
    DESCRIPTION
        "The interval over which monitored value is
        sampled and compared with the specified threshold."
    ::= { cmL3FlowPointThresholdEntry 2 }

cmL3FlowPointThresholdVariable OBJECT-TYPE
    SYNTAX     VariablePointer
    MAX-ACCESS read-only
    STATUS     current
    DESCRIPTION
        "The object identifier of the particular variable to be
        sampled."
    ::= { cmL3FlowPointThresholdEntry 3 }

cmL3FlowPointThresholdValueLo OBJECT-TYPE
    SYNTAX     Unsigned32
    MAX-ACCESS read-write
    STATUS     current
    DESCRIPTION
        "Lower 32 bits of the threshold value."
    ::= { cmL3FlowPointThresholdEntry 4 }

cmL3FlowPointThresholdValueHi OBJECT-TYPE
    SYNTAX     Unsigned32
    MAX-ACCESS read-write
    STATUS     current
    DESCRIPTION
        "Higher 32 bits of the threshold value."
    ::= { cmL3FlowPointThresholdEntry 5 }

cmL3FlowPointThresholdMonValue OBJECT-TYPE
    SYNTAX     Counter64
    MAX-ACCESS read-only
    STATUS     current
    DESCRIPTION
        "Monitored value corresponding to cmL3FlowPointThresholdVariable."
    ::= { cmL3FlowPointThresholdEntry 6 }


--
-- Quality of Service(QOS) Policer Current Statistics Table
--
cmL3QosPolicerStatsTable OBJECT-TYPE
    SYNTAX      SEQUENCE OF CML3QosPolicerStatsEntry
    MAX-ACCESS  not-accessible
    STATUS      current
    DESCRIPTION
            "A collection of QOS Policer statistics.  
             These reflect the current data."
    ::= { f3L3Performance 28 }

cmL3QosPolicerStatsEntry OBJECT-TYPE
    SYNTAX      CML3QosPolicerStatsEntry 
    MAX-ACCESS  not-accessible
    STATUS      current
    DESCRIPTION
            "A conceptual row in the cmL3QosPolicerStatsTable.
             Entries exist in this table for each l3 flow point policer."
    INDEX { neIndex, shelfIndex, slotIndex, 
            cmL3FlowPointPortIndex, cmL3FlowPointIndex, cmL3QosPolicerIndex,
            cmL3QosPolicerStatsIndex }
    ::= { cmL3QosPolicerStatsTable 1 }

CML3QosPolicerStatsEntry ::= SEQUENCE {
    cmL3QosPolicerStatsIndex           Integer32,
    cmL3QosPolicerStatsIntervalType    CmPmIntervalType,
    cmL3QosPolicerStatsValid           TruthValue,
    cmL3QosPolicerStatsAction          CmPmBinAction,
    cmL3QosPolicerStatsFMG             PerfCounter64,
    cmL3QosPolicerStatsFMY             PerfCounter64,
    cmL3QosPolicerStatsFMYD            PerfCounter64,
    cmL3QosPolicerStatsFMRD            PerfCounter64,
    cmL3QosPolicerStatsBytesIn         PerfCounter64,
    cmL3QosPolicerStatsBytesOut        PerfCounter64,
    cmL3QosPolicerStatsABR             PerfCounter64
}

cmL3QosPolicerStatsIndex OBJECT-TYPE
    SYNTAX      Integer32 (1..65535)
    MAX-ACCESS  read-only
    STATUS      current
    DESCRIPTION
            "An integer index value used to uniquely identify
            this QOS Policer statistics entry.
            1 - 15min
            2 - 1day
            3 - rollover
            4 - 5min"
    ::= { cmL3QosPolicerStatsEntry 1 }

cmL3QosPolicerStatsIntervalType OBJECT-TYPE
    SYNTAX      CmPmIntervalType
    MAX-ACCESS  read-only
    STATUS      current
    DESCRIPTION
            "Interval over which Performance Monitoring data is collected."
    ::= { cmL3QosPolicerStatsEntry 2 }

cmL3QosPolicerStatsValid OBJECT-TYPE
    SYNTAX      TruthValue
    MAX-ACCESS  read-only
    STATUS      current
    DESCRIPTION
            "Indicates the validity of the bin."
    ::= { cmL3QosPolicerStatsEntry 3 }

cmL3QosPolicerStatsAction OBJECT-TYPE
    SYNTAX      CmPmBinAction
    MAX-ACCESS  read-write
    STATUS      current
    DESCRIPTION
            "Allows the Manager to clear the bin."
    ::= { cmL3QosPolicerStatsEntry 4 }

cmL3QosPolicerStatsFMG OBJECT-TYPE
     SYNTAX     PerfCounter64
     MAX-ACCESS read-only
     STATUS     current
     DESCRIPTION
         "Frames Marked Green."
     ::= { cmL3QosPolicerStatsEntry 5 }

cmL3QosPolicerStatsFMY OBJECT-TYPE
     SYNTAX     PerfCounter64
     MAX-ACCESS read-only
     STATUS     current
     DESCRIPTION
         "Frames Marked Yellow."
     ::= { cmL3QosPolicerStatsEntry 6 }

cmL3QosPolicerStatsFMYD OBJECT-TYPE
     SYNTAX     PerfCounter64
     MAX-ACCESS read-only
     STATUS     deprecated
     DESCRIPTION
         "Frames Marked Yellow and Dropped."
     ::= { cmL3QosPolicerStatsEntry 7 }

cmL3QosPolicerStatsFMRD OBJECT-TYPE
     SYNTAX     PerfCounter64
     MAX-ACCESS read-only
     STATUS     current
     DESCRIPTION
         "Frames Marked Red and Discarded."
     ::= { cmL3QosPolicerStatsEntry 8 }

cmL3QosPolicerStatsBytesIn OBJECT-TYPE
     SYNTAX     PerfCounter64
     MAX-ACCESS read-only
     STATUS     current
     DESCRIPTION
         "Number of bytes received by the Policer."
     ::= { cmL3QosPolicerStatsEntry 9 }

cmL3QosPolicerStatsBytesOut OBJECT-TYPE
     SYNTAX     PerfCounter64
     MAX-ACCESS read-only
     STATUS     current
     DESCRIPTION
         "Number of bytes transmitted by the Policer."
     ::= { cmL3QosPolicerStatsEntry 10 }

cmL3QosPolicerStatsABR OBJECT-TYPE
     SYNTAX     PerfCounter64
     MAX-ACCESS read-only
     STATUS     current
     DESCRIPTION
         "Average Bit Rate  on the Policer."
     ::= { cmL3QosPolicerStatsEntry 11 }


--
-- Quality of Service(QOS) Policer History Statistics Table
--
cmL3QosPolicerHistoryTable OBJECT-TYPE
    SYNTAX      SEQUENCE OF CML3QosPolicerHistoryEntry
    MAX-ACCESS  not-accessible
    STATUS      current
    DESCRIPTION
            "A collection of QOS Policer statistics.  
             These reflect the current data."
    ::= { f3L3Performance 29 }

cmL3QosPolicerHistoryEntry OBJECT-TYPE
    SYNTAX      CML3QosPolicerHistoryEntry 
    MAX-ACCESS  not-accessible
    STATUS      current
    DESCRIPTION
            "A conceptual row in the cmL3QosPolicerHistoryTable.
             Entries exist in this table for each flow point policer."
    INDEX { neIndex, shelfIndex, slotIndex, 
            cmL3FlowPointPortIndex, cmL3FlowPointIndex, cmL3QosPolicerIndex,
            cmL3QosPolicerStatsIndex, cmL3QosPolicerHistoryIndex }
    ::= { cmL3QosPolicerHistoryTable 1 }

CML3QosPolicerHistoryEntry ::= SEQUENCE {
    cmL3QosPolicerHistoryIndex           Integer32,
    cmL3QosPolicerHistoryTime            DateAndTime,
    cmL3QosPolicerHistoryValid           TruthValue,
    cmL3QosPolicerHistoryAction          CmPmBinAction,
    cmL3QosPolicerHistoryFMG             PerfCounter64,
    cmL3QosPolicerHistoryFMY             PerfCounter64,
    cmL3QosPolicerHistoryFMYD            PerfCounter64,
    cmL3QosPolicerHistoryFMRD            PerfCounter64,
    cmL3QosPolicerHistoryBytesIn         PerfCounter64,
    cmL3QosPolicerHistoryBytesOut        PerfCounter64,
    cmL3QosPolicerHistoryABR             PerfCounter64
}

cmL3QosPolicerHistoryIndex OBJECT-TYPE
    SYNTAX      Integer32 (1..65535)
    MAX-ACCESS  read-only
    STATUS      current
    DESCRIPTION
            "An arbitrary integer index value used to uniquely identify
            this QOS Policer history entry."
    ::= { cmL3QosPolicerHistoryEntry 1 }

cmL3QosPolicerHistoryTime OBJECT-TYPE
    SYNTAX      DateAndTime
    MAX-ACCESS  read-only
    STATUS      current
    DESCRIPTION
            "Indicates the time of history bin creation." 
    ::= { cmL3QosPolicerHistoryEntry 2 }

cmL3QosPolicerHistoryValid OBJECT-TYPE
    SYNTAX      TruthValue
    MAX-ACCESS  read-only
    STATUS      current
    DESCRIPTION
            "Indicates the validity of the bin."
    ::= { cmL3QosPolicerHistoryEntry 3 }

cmL3QosPolicerHistoryAction OBJECT-TYPE
    SYNTAX      CmPmBinAction
    MAX-ACCESS  read-write
    STATUS      current
    DESCRIPTION
            "Allows the Manager to clear the bin."
    ::= { cmL3QosPolicerHistoryEntry 4 }

cmL3QosPolicerHistoryFMG OBJECT-TYPE
     SYNTAX     PerfCounter64
     MAX-ACCESS read-only
     STATUS     current
     DESCRIPTION
         "Frames Marked Green."
     ::= { cmL3QosPolicerHistoryEntry 5 }

cmL3QosPolicerHistoryFMY OBJECT-TYPE
     SYNTAX     PerfCounter64
     MAX-ACCESS read-only
     STATUS     current
     DESCRIPTION
         "Frames Marked Yellow."
     ::= { cmL3QosPolicerHistoryEntry 6 }

cmL3QosPolicerHistoryFMYD OBJECT-TYPE
     SYNTAX     PerfCounter64
     MAX-ACCESS read-only
     STATUS     deprecated
     DESCRIPTION
         "Frames Marked Yellow and Dropped."
     ::= { cmL3QosPolicerHistoryEntry 7 }

cmL3QosPolicerHistoryFMRD OBJECT-TYPE
     SYNTAX     PerfCounter64
     MAX-ACCESS read-only
     STATUS     current
     DESCRIPTION
         "Frames Marked Red and Discarded."
     ::= { cmL3QosPolicerHistoryEntry 8 }

cmL3QosPolicerHistoryBytesIn OBJECT-TYPE
     SYNTAX     PerfCounter64
     MAX-ACCESS read-only
     STATUS     current
     DESCRIPTION
         "Number of bytes received by the Policer."
     ::= { cmL3QosPolicerHistoryEntry 9 }

cmL3QosPolicerHistoryBytesOut OBJECT-TYPE
     SYNTAX     PerfCounter64
     MAX-ACCESS read-only
     STATUS     current
     DESCRIPTION
         "Number of bytes transmitted by the Policer."
     ::= { cmL3QosPolicerHistoryEntry 10 }

cmL3QosPolicerHistoryABR OBJECT-TYPE
     SYNTAX     PerfCounter64
     MAX-ACCESS read-only
     STATUS     current
     DESCRIPTION
         "Average Bit Rate  on the Policer."
     ::= { cmL3QosPolicerHistoryEntry 11 }

--
-- QOS Policer Threshold Table
--
cmL3QosPolicerThresholdTable OBJECT-TYPE
    SYNTAX      SEQUENCE OF CML3QosPolicerThresholdEntry
    MAX-ACCESS  not-accessible
    STATUS      current
    DESCRIPTION
            "A table of entries that allow manageability of QOS
             Policer Thresholds."
    ::= { f3L3Performance 30 }

cmL3QosPolicerThresholdEntry OBJECT-TYPE
    SYNTAX      CML3QosPolicerThresholdEntry
    MAX-ACCESS  not-accessible
    STATUS      current
    DESCRIPTION
            "A conceptual row in the cmL3QosPolicerThresholdTable."
    INDEX { neIndex, shelfIndex, slotIndex, 
            cmL3FlowPointPortIndex, cmL3FlowPointIndex, cmL3QosPolicerIndex,
            cmL3QosPolicerStatsIndex, cmL3QosPolicerThresholdIndex }
    ::= { cmL3QosPolicerThresholdTable 1 }

CML3QosPolicerThresholdEntry ::= SEQUENCE {
    cmL3QosPolicerThresholdIndex       Integer32,
    cmL3QosPolicerThresholdInterval    CmPmIntervalType,
    cmL3QosPolicerThresholdVariable    VariablePointer,
    cmL3QosPolicerThresholdValueLo     Unsigned32,
    cmL3QosPolicerThresholdValueHi     Unsigned32,
    cmL3QosPolicerThresholdMonValue    Counter64
}

cmL3QosPolicerThresholdIndex OBJECT-TYPE
    SYNTAX     Integer32 (1..65535)
    MAX-ACCESS read-only
    STATUS     current
    DESCRIPTION
        "An index that uniquely identifies an entry in the
        cmL3QosPolicerThresholdTable."
    ::= { cmL3QosPolicerThresholdEntry 1 }

cmL3QosPolicerThresholdInterval OBJECT-TYPE
    SYNTAX     CmPmIntervalType
    MAX-ACCESS read-only
    STATUS     current
    DESCRIPTION
        "The interval over which monitored value is
        sampled and compared with the specified threshold."
    ::= { cmL3QosPolicerThresholdEntry 2 }

cmL3QosPolicerThresholdVariable OBJECT-TYPE
    SYNTAX     VariablePointer
    MAX-ACCESS read-only
    STATUS     current
    DESCRIPTION
        "The object identifier of the particular variable to be
        sampled."
    ::= { cmL3QosPolicerThresholdEntry 3 }

cmL3QosPolicerThresholdValueLo OBJECT-TYPE
    SYNTAX     Unsigned32
    MAX-ACCESS read-write
    STATUS     current
    DESCRIPTION
        "Lower 32 bits of the threshold value."
    ::= { cmL3QosPolicerThresholdEntry 4 }

cmL3QosPolicerThresholdValueHi OBJECT-TYPE
    SYNTAX     Unsigned32
    MAX-ACCESS read-write
    STATUS     current
    DESCRIPTION
        "Higher 32 bits of the threshold value."
    ::= { cmL3QosPolicerThresholdEntry 5 }

cmL3QosPolicerThresholdMonValue OBJECT-TYPE
    SYNTAX     Counter64
    MAX-ACCESS read-only
    STATUS     current
    DESCRIPTION
        "Monitored value corresponding to cmL3QosPolicerThresholdVariable."
    ::= { cmL3QosPolicerThresholdEntry 6 }

--
-- L3 flow point Level Quality of Service(QOS) Shaper Current Statistics Table
--
cmL3QosShaperStatsTable OBJECT-TYPE
    SYNTAX      SEQUENCE OF CML3QosShaperStatsEntry
    MAX-ACCESS  not-accessible
    STATUS      current
    DESCRIPTION
            "A collection of L3 flow point Level QOS Shaper statistics.  
             These reflect the current data."
    ::= { f3L3Performance 31 }

cmL3QosShaperStatsEntry OBJECT-TYPE
    SYNTAX      CML3QosShaperStatsEntry 
    MAX-ACCESS  not-accessible
    STATUS      current
    DESCRIPTION
            "A conceptual row in the cmL3QosShaperStatsTable.
             Entries exist in this table for each QOS Shaper per L3 flow point."
    INDEX { neIndex, shelfIndex, slotIndex, 
            cmL3FlowPointPortIndex, cmL3FlowPointIndex,
            cmL3QosShaperIndex, cmL3QosShaperStatsIndex }
    ::= { cmL3QosShaperStatsTable 1 }

CML3QosShaperStatsEntry ::= SEQUENCE {
    cmL3QosShaperStatsIndex             Integer32,
    cmL3QosShaperStatsIntervalType      CmPmIntervalType,
    cmL3QosShaperStatsValid             TruthValue,
    cmL3QosShaperStatsAction            CmPmBinAction,
    cmL3QosShaperStatsBT                PerfCounter64,
    cmL3QosShaperStatsBTD               PerfCounter64,
    cmL3QosShaperStatsFD                PerfCounter64,
    cmL3QosShaperStatsFTD               PerfCounter64,
    cmL3QosShaperStatsBR                PerfCounter64,
    cmL3QosShaperStatsFR                PerfCounter64,
    cmL3QosShaperStatsABRRL             PerfCounter64,
    cmL3QosShaperStatsABRRLR            PerfCounter64,
    cmL3QosShaperStatsBREDD             PerfCounter64,
    cmL3QosShaperStatsFREDD             PerfCounter64
}

cmL3QosShaperStatsIndex OBJECT-TYPE
    SYNTAX      Integer32 (1..65535)
    MAX-ACCESS  read-only
    STATUS      current
    DESCRIPTION
            "An arbitrary integer index value used to uniquely identify
            this QOS Shaper statistics entry.
            1 - 15min
            2 - 1day
            3 - rollover
            4 - 5min"
    ::= { cmL3QosShaperStatsEntry 1 }

cmL3QosShaperStatsIntervalType OBJECT-TYPE
    SYNTAX      CmPmIntervalType
    MAX-ACCESS  read-only
    STATUS      current
    DESCRIPTION
            "Interval over which Performance Monitoring data is collected."
    ::= { cmL3QosShaperStatsEntry 2 }

cmL3QosShaperStatsValid OBJECT-TYPE
    SYNTAX      TruthValue
    MAX-ACCESS  read-only
    STATUS      current
    DESCRIPTION
            "Indicates the validity of the bin."
    ::= { cmL3QosShaperStatsEntry 3 }

cmL3QosShaperStatsAction OBJECT-TYPE
    SYNTAX      CmPmBinAction
    MAX-ACCESS  read-write
    STATUS      current
    DESCRIPTION
            "Allows the Manager to clear the bin."
    ::= { cmL3QosShaperStatsEntry 4 }

cmL3QosShaperStatsBT OBJECT-TYPE
     SYNTAX     PerfCounter64
     MAX-ACCESS read-only
     STATUS     current
     DESCRIPTION
         "Bytes Transmitted."
     ::= { cmL3QosShaperStatsEntry 5 }

cmL3QosShaperStatsBTD OBJECT-TYPE
     SYNTAX     PerfCounter64
     MAX-ACCESS read-only
     STATUS     current
     DESCRIPTION
         "Bytes Tail Dropped."
     ::= { cmL3QosShaperStatsEntry 6 }

cmL3QosShaperStatsFD OBJECT-TYPE
     SYNTAX     PerfCounter64
     MAX-ACCESS read-only
     STATUS     current
     DESCRIPTION
         "Frames Dequeued."
     ::= { cmL3QosShaperStatsEntry 7 }

cmL3QosShaperStatsFTD OBJECT-TYPE
     SYNTAX     PerfCounter64
     MAX-ACCESS read-only
     STATUS     current
     DESCRIPTION
         "Frames Tail Dropped."
     ::= { cmL3QosShaperStatsEntry 8 }

cmL3QosShaperStatsBR OBJECT-TYPE
     SYNTAX     PerfCounter64
     MAX-ACCESS read-only
     STATUS     current
     DESCRIPTION
         "Bytes Replicated."
     ::= { cmL3QosShaperStatsEntry 9 }

cmL3QosShaperStatsFR OBJECT-TYPE
     SYNTAX     PerfCounter64
     MAX-ACCESS read-only
     STATUS     current
     DESCRIPTION
         "Frames Replicated."
     ::= { cmL3QosShaperStatsEntry 10 }

cmL3QosShaperStatsABRRL OBJECT-TYPE
     SYNTAX     PerfCounter64
     MAX-ACCESS read-only
     STATUS     current
     DESCRIPTION
         "Average Bit Rate - Rate Limited."
     ::= { cmL3QosShaperStatsEntry 11 }

cmL3QosShaperStatsABRRLR OBJECT-TYPE
     SYNTAX     PerfCounter64
     MAX-ACCESS read-only
     STATUS     current
     DESCRIPTION
         "Average Bit Rate - Rate Limited, Replicated."
     ::= { cmL3QosShaperStatsEntry 12 }

cmL3QosShaperStatsBREDD OBJECT-TYPE
     SYNTAX     PerfCounter64
     MAX-ACCESS read-only
     STATUS     current
     DESCRIPTION
         "Bytes Random Early Discard, Dropped."
     ::= { cmL3QosShaperStatsEntry 13 }

cmL3QosShaperStatsFREDD OBJECT-TYPE
     SYNTAX     PerfCounter64
     MAX-ACCESS read-only
     STATUS     current
     DESCRIPTION
         "Frames Random Early Discard, Dropped."
     ::= { cmL3QosShaperStatsEntry 14 }

--
-- Quality of Service(QOS) Shaper History Statistics Table
--
cmL3QosShaperHistoryTable OBJECT-TYPE
    SYNTAX      SEQUENCE OF CML3QosShaperHistoryEntry
    MAX-ACCESS  not-accessible
    STATUS      current
    DESCRIPTION
            "A collection of l3 flow point Level QOS Shaper statistics.
             These reflect the history data."
    ::= { f3L3Performance 32 }

cmL3QosShaperHistoryEntry OBJECT-TYPE
    SYNTAX      CML3QosShaperHistoryEntry 
    MAX-ACCESS  not-accessible
    STATUS      current
    DESCRIPTION
            "A conceptual row in the cmL3QosShaperHistoryTable.
             Entries exist in this table for each Shaper per l3 flow point."
    INDEX { neIndex, shelfIndex, slotIndex, 
            cmL3FlowPointPortIndex, cmL3FlowPointIndex,
            cmL3QosShaperIndex, cmL3QosShaperStatsIndex, cmL3QosShaperHistoryIndex }
    ::= { cmL3QosShaperHistoryTable 1 }

CML3QosShaperHistoryEntry ::= SEQUENCE {
    cmL3QosShaperHistoryIndex             Integer32,
    cmL3QosShaperHistoryTime              DateAndTime,
    cmL3QosShaperHistoryValid             TruthValue,
    cmL3QosShaperHistoryAction            CmPmBinAction,
    cmL3QosShaperHistoryBT                PerfCounter64,
    cmL3QosShaperHistoryBTD               PerfCounter64,
    cmL3QosShaperHistoryFD                PerfCounter64,
    cmL3QosShaperHistoryFTD               PerfCounter64,
    cmL3QosShaperHistoryBR                PerfCounter64,
    cmL3QosShaperHistoryFR                PerfCounter64,
    cmL3QosShaperHistoryABRRL             PerfCounter64,
    cmL3QosShaperHistoryABRRLR            PerfCounter64,
    cmL3QosShaperHistoryBREDD             PerfCounter64,
    cmL3QosShaperHistoryFREDD             PerfCounter64
}

cmL3QosShaperHistoryIndex OBJECT-TYPE
    SYNTAX      Integer32 (1..65535)
    MAX-ACCESS  read-only
    STATUS      current
    DESCRIPTION
            "An arbitrary integer index value used to uniquely identify
            this QOS Shaper statistics entry."
    ::= { cmL3QosShaperHistoryEntry 1 }

cmL3QosShaperHistoryTime OBJECT-TYPE
    SYNTAX      DateAndTime
    MAX-ACCESS  read-only
    STATUS      current
    DESCRIPTION
            "Indicates the time of history bin creation." 
    ::= { cmL3QosShaperHistoryEntry 2 }

cmL3QosShaperHistoryValid OBJECT-TYPE
    SYNTAX      TruthValue
    MAX-ACCESS  read-only
    STATUS      current
    DESCRIPTION
            "Indicates the validity of the bin."
    ::= { cmL3QosShaperHistoryEntry 3 }

cmL3QosShaperHistoryAction OBJECT-TYPE
    SYNTAX      CmPmBinAction
    MAX-ACCESS  read-write
    STATUS      current
    DESCRIPTION
            "Allows the Manager to clear the bin."
    ::= { cmL3QosShaperHistoryEntry 4 }

cmL3QosShaperHistoryBT OBJECT-TYPE
     SYNTAX     PerfCounter64
     MAX-ACCESS read-only
     STATUS     current
     DESCRIPTION
         "Bytes Transmitted."
     ::= { cmL3QosShaperHistoryEntry 5 }

cmL3QosShaperHistoryBTD OBJECT-TYPE
     SYNTAX     PerfCounter64
     MAX-ACCESS read-only
     STATUS     current
     DESCRIPTION
         "Bytes Tail Dropped."
     ::= { cmL3QosShaperHistoryEntry 6 }

cmL3QosShaperHistoryFD OBJECT-TYPE
     SYNTAX     PerfCounter64
     MAX-ACCESS read-only
     STATUS     current
     DESCRIPTION
         "Frames Dequeued."
     ::= { cmL3QosShaperHistoryEntry 7 }

cmL3QosShaperHistoryFTD OBJECT-TYPE
     SYNTAX     PerfCounter64
     MAX-ACCESS read-only
     STATUS     current
     DESCRIPTION
         "Frames Tail Dropped."
     ::= { cmL3QosShaperHistoryEntry 8 }

cmL3QosShaperHistoryBR OBJECT-TYPE
     SYNTAX     PerfCounter64
     MAX-ACCESS read-only
     STATUS     current
     DESCRIPTION
         "Bytes Replicated."
     ::= { cmL3QosShaperHistoryEntry 9 }

cmL3QosShaperHistoryFR OBJECT-TYPE
     SYNTAX     PerfCounter64
     MAX-ACCESS read-only
     STATUS     current
     DESCRIPTION
         "Frames Replicated."
     ::= { cmL3QosShaperHistoryEntry 10 }

cmL3QosShaperHistoryABRRL OBJECT-TYPE
     SYNTAX     PerfCounter64
     MAX-ACCESS read-only
     STATUS     current
     DESCRIPTION
         "Average Bit Rate - Rate Limited."
     ::= { cmL3QosShaperHistoryEntry 11 }

cmL3QosShaperHistoryABRRLR OBJECT-TYPE
     SYNTAX     PerfCounter64
     MAX-ACCESS read-only
     STATUS     current
     DESCRIPTION
         "Average Bit Rate - Rate Limited, Replicated."
     ::= { cmL3QosShaperHistoryEntry 12 }

cmL3QosShaperHistoryBREDD OBJECT-TYPE
     SYNTAX     PerfCounter64
     MAX-ACCESS read-only
     STATUS     current
     DESCRIPTION
         "Bytes Random Early Discard, Dropped."
     ::= { cmL3QosShaperHistoryEntry 13 }

cmL3QosShaperHistoryFREDD OBJECT-TYPE
     SYNTAX     PerfCounter64
     MAX-ACCESS read-only
     STATUS     current
     DESCRIPTION
         "Frames Random Early Discard, Dropped."
     ::= { cmL3QosShaperHistoryEntry 14 }

--
-- L3 flow point QOS Shaper Threshold Table
--
cmL3QosShaperThresholdTable OBJECT-TYPE
    SYNTAX      SEQUENCE OF CML3QosShaperThresholdEntry
    MAX-ACCESS  not-accessible
    STATUS      current
    DESCRIPTION
            "A table of entries that allow manageability of QOS
             Shaper Thresholds."
    ::= { f3L3Performance 33 }

cmL3QosShaperThresholdEntry OBJECT-TYPE
    SYNTAX      CML3QosShaperThresholdEntry
    MAX-ACCESS  not-accessible
    STATUS      current
    DESCRIPTION
            "A conceptual row in the cmL3QosShaperThresholdTable."
    INDEX { neIndex, shelfIndex, slotIndex, 
            cmL3FlowPointPortIndex, cmL3FlowPointIndex,
            cmL3QosShaperIndex, cmL3QosShaperStatsIndex, 
            cmL3QosShaperThresholdIndex }
    ::= { cmL3QosShaperThresholdTable 1 }

CML3QosShaperThresholdEntry ::= SEQUENCE {
    cmL3QosShaperThresholdIndex       Integer32,
    cmL3QosShaperThresholdInterval    CmPmIntervalType,
    cmL3QosShaperThresholdVariable    VariablePointer,
    cmL3QosShaperThresholdValueLo     Unsigned32,
    cmL3QosShaperThresholdValueHi     Unsigned32,
    cmL3QosShaperThresholdMonValue    Counter64
}

cmL3QosShaperThresholdIndex OBJECT-TYPE
    SYNTAX     Integer32 (1..65535)
    MAX-ACCESS read-only
    STATUS     current
    DESCRIPTION
        "An index that uniquely identifies an entry in the
        cmL3QosShaperThresholdTable."
    ::= { cmL3QosShaperThresholdEntry 1 }

cmL3QosShaperThresholdInterval OBJECT-TYPE
    SYNTAX     CmPmIntervalType
    MAX-ACCESS read-only
    STATUS     current
    DESCRIPTION
        "The interval over which monitored value is
        sampled and compared with the specified threshold."
    ::= { cmL3QosShaperThresholdEntry 2 }

cmL3QosShaperThresholdVariable OBJECT-TYPE
    SYNTAX     VariablePointer
    MAX-ACCESS read-only
    STATUS     current
    DESCRIPTION
        "The object identifier of the particular variable to be
        sampled."
    ::= { cmL3QosShaperThresholdEntry 3 }

cmL3QosShaperThresholdValueLo OBJECT-TYPE
    SYNTAX     Unsigned32
    MAX-ACCESS read-write
    STATUS     current
    DESCRIPTION
        "Lower 32 bits of the threshold value."
    ::= { cmL3QosShaperThresholdEntry 4 }

cmL3QosShaperThresholdValueHi OBJECT-TYPE
    SYNTAX     Unsigned32
    MAX-ACCESS read-write
    STATUS     current
    DESCRIPTION
        "Higher 32 bits of the threshold value."
    ::= { cmL3QosShaperThresholdEntry 5 }

cmL3QosShaperThresholdMonValue OBJECT-TYPE
    SYNTAX     Counter64
    MAX-ACCESS read-only
    STATUS     current
    DESCRIPTION
        "Monitored value corresponding to cmL3QosShaperThresholdVariable."
    ::= { cmL3QosShaperThresholdEntry 6 }


--
-- L3 Dhcp Class Table
--
f3L3DhcpClassTable  OBJECT-TYPE
    SYNTAX      SEQUENCE OF F3L3DhcpClassEntry
    MAX-ACCESS  not-accessible
    STATUS      current
    DESCRIPTION
        "A list of L3 Dhcp Class fsp150 family of products."
    ::= { f3L3Objects 54 }

f3L3DhcpClassEntry  OBJECT-TYPE
    SYNTAX      F3L3DhcpClassEntry
    MAX-ACCESS  not-accessible
    STATUS      current
    DESCRIPTION
        "A conceptual row in the f3L3DhcpClassTable. Entries can
        be created/deleted in this table by management application action."
    INDEX { neIndex,
            shelfIndex,
            slotIndex,
            f3L3FlowPointPortIndex,
            f3L3FlowPointIndex,
            f3L3TrafficIPIfIndex,
            f3L3DhcpClassIndex }
    ::= { f3L3DhcpClassTable 1 }

F3L3DhcpClassEntry ::= SEQUENCE {
      f3L3DhcpClassIndex          Integer32,
      f3L3DhcpClassStorageType    StorageType,
      f3L3DhcpClassRowStatus      RowStatus
    }

f3L3DhcpClassIndex OBJECT-TYPE
    SYNTAX      Integer32 
    MAX-ACCESS  not-accessible
    STATUS      current
    DESCRIPTION
        "A unique index value used to uniquely identify a entry."
    ::= { f3L3DhcpClassEntry 1 }

f3L3DhcpClassStorageType OBJECT-TYPE
    SYNTAX      StorageType 
    MAX-ACCESS  read-create
    STATUS      current
    DESCRIPTION
        "The type of storage configured for this entry."
    ::= { f3L3DhcpClassEntry 2 }

f3L3DhcpClassRowStatus OBJECT-TYPE
    SYNTAX      RowStatus 
    MAX-ACCESS  read-create
    STATUS      current
    DESCRIPTION
        "The status of this row. The object may be modified
        if the associated instance of this object is equal
        to active(1), notInService(2), or notReady(3)."
    ::= { f3L3DhcpClassEntry 3 }

--
-- L3 Dhcp Rule Table
--
f3L3DhcpRuleTable  OBJECT-TYPE
    SYNTAX      SEQUENCE OF F3L3DhcpRuleEntry
    MAX-ACCESS  not-accessible
    STATUS      current
    DESCRIPTION
        "A list of L3 Dhcp Rule fsp150 family of products."
    ::= { f3L3Objects 55 }

f3L3DhcpRuleEntry  OBJECT-TYPE
    SYNTAX      F3L3DhcpRuleEntry
    MAX-ACCESS  not-accessible
    STATUS      current
    DESCRIPTION
        "A conceptual row in the f3L3DhcpRuleTable. Entries can
        be created/deleted in this table by management application action."
    INDEX { neIndex,
            shelfIndex,
            slotIndex,
            f3L3FlowPointPortIndex,
            f3L3FlowPointIndex,
            f3L3TrafficIPIfIndex,
            f3L3DhcpClassIndex,
            f3L3DhcpRuleIndex }
    ::= { f3L3DhcpRuleTable 1 }

F3L3DhcpRuleEntry ::= SEQUENCE {
      f3L3DhcpRuleIndex          Integer32,
      f3L3DhcpRuleType           DhcpMatchType,
      f3L3DhcpRuleValue          DisplayString,
      f3L3DhcpRuleStorageType    StorageType,
      f3L3DhcpRuleRowStatus      RowStatus
    }

f3L3DhcpRuleIndex OBJECT-TYPE
    SYNTAX      Integer32 
    MAX-ACCESS  not-accessible
    STATUS      current
    DESCRIPTION
        "A unique index value used to uniquely identify a entry."
    ::= { f3L3DhcpRuleEntry 1 }

f3L3DhcpRuleType OBJECT-TYPE
    SYNTAX      DhcpMatchType 
    MAX-ACCESS  read-create
    STATUS      current
    DESCRIPTION
        "This indicates to compare source MAC address or
        Vendor Class-ID from received packet."
    ::= { f3L3DhcpRuleEntry 2 }

f3L3DhcpRuleValue OBJECT-TYPE
    SYNTAX      DisplayString
    MAX-ACCESS  read-create
    STATUS      current
    DESCRIPTION
        "The value of MAC address or Class ID string to be compared."
    ::= { f3L3DhcpRuleEntry 3 }

f3L3DhcpRuleStorageType OBJECT-TYPE
    SYNTAX      StorageType 
    MAX-ACCESS  read-create
    STATUS      current
    DESCRIPTION
        "The type of storage configured for this entry."
    ::= { f3L3DhcpRuleEntry 4 }

f3L3DhcpRuleRowStatus OBJECT-TYPE
    SYNTAX      RowStatus 
    MAX-ACCESS  read-create
    STATUS      current
    DESCRIPTION
        "The status of this row. The object may be modified
        if the associated instance of this object is equal
        to active(1), notInService(2), or notReady(3)."
    ::= { f3L3DhcpRuleEntry 5 }

--
-- L3 Dhcp IPv4 Addr Pool Table
--
f3L3DhcpIPv4AddrPoolTable  OBJECT-TYPE
    SYNTAX      SEQUENCE OF F3L3DhcpIPv4AddrPoolEntry
    MAX-ACCESS  not-accessible
    STATUS      current
    DESCRIPTION
        "A list of L3 Dhcp IPv4 Addr Pool fsp150 family of products."
    ::= { f3L3Objects 56 }

f3L3DhcpIPv4AddrPoolEntry  OBJECT-TYPE
    SYNTAX      F3L3DhcpIPv4AddrPoolEntry
    MAX-ACCESS  not-accessible
    STATUS      current
    DESCRIPTION
        "A conceptual row in the f3L3DhcpIPv4AddrPoolTable. Entries can
        be created/deleted in this table by management application action."
    INDEX { neIndex,
            shelfIndex,
            slotIndex,
            f3L3FlowPointPortIndex,
            f3L3FlowPointIndex,
            f3L3TrafficIPIfIndex,
            f3L3DhcpIPv4AddrPoolIndex }
    ::= { f3L3DhcpIPv4AddrPoolTable 1 }

F3L3DhcpIPv4AddrPoolEntry ::= SEQUENCE {
      f3L3DhcpIPv4AddrPoolIndex             Integer32,
      f3L3DhcpIPv4AddrPoolStartAddr         IpAddress,
      f3L3DhcpIPv4AddrPoolEndAddr           IpAddress,
      f3L3DhcpIPv4AddrPoolClass             VariablePointer,
      f3L3DhcpIPv4AddrPoolLeaseTime         Unsigned32,
      f3L3DhcpIPv4AddrPoolGatewayList       DisplayString,
      f3L3DhcpIPv4AddrPoolDnsList           DisplayString,
      f3L3DhcpIPv4AddrPoolTotalCount        Unsigned32,
      f3L3DhcpIPv4AddrPoolAllocatedCount    Unsigned32,
      f3L3DhcpIPv4AddrPoolAction            DhcpIPv4AddrPoolActionType,
      f3L3DhcpIPv4AddrPoolActionIPv4Addr    IpAddress,
      f3L3DhcpIPv4AddrPoolStorageType       StorageType,
      f3L3DhcpIPv4AddrPoolRowStatus         RowStatus
    }

f3L3DhcpIPv4AddrPoolIndex OBJECT-TYPE
    SYNTAX      Integer32 
    MAX-ACCESS  not-accessible
    STATUS      current
    DESCRIPTION
        "A unique index value used to uniquely identify a entry."
    ::= { f3L3DhcpIPv4AddrPoolEntry 1 }

f3L3DhcpIPv4AddrPoolStartAddr OBJECT-TYPE
    SYNTAX      IpAddress 
    MAX-ACCESS  read-create
    STATUS      current
    DESCRIPTION
        "The start address of DHCP address pool."
    ::= { f3L3DhcpIPv4AddrPoolEntry 2 }

f3L3DhcpIPv4AddrPoolEndAddr OBJECT-TYPE
    SYNTAX      IpAddress 
    MAX-ACCESS  read-create
    STATUS      current
    DESCRIPTION
        "The end address of DHCP address pool."
    ::= { f3L3DhcpIPv4AddrPoolEntry 3 }

f3L3DhcpIPv4AddrPoolClass OBJECT-TYPE
    SYNTAX      VariablePointer 
    MAX-ACCESS  read-create
    STATUS      current
    DESCRIPTION
        "The rule match in the DHCP class for the pool IP
        address allocation."
    ::= { f3L3DhcpIPv4AddrPoolEntry 4 }

f3L3DhcpIPv4AddrPoolLeaseTime OBJECT-TYPE
    SYNTAX      Unsigned32 
    MAX-ACCESS  read-create
    STATUS      current
    DESCRIPTION
        "The time in seconds, from 120 to 31536000 (365
        days),0xffffffff means infinite."
    ::= { f3L3DhcpIPv4AddrPoolEntry 5 }

f3L3DhcpIPv4AddrPoolGatewayList OBJECT-TYPE
    SYNTAX      DisplayString 
    MAX-ACCESS  read-create
    STATUS      current
    DESCRIPTION
        "Gateway list. should be valid unicast address."
    ::= { f3L3DhcpIPv4AddrPoolEntry 6 }

f3L3DhcpIPv4AddrPoolDnsList OBJECT-TYPE
    SYNTAX      DisplayString 
    MAX-ACCESS  read-create
    STATUS      current
    DESCRIPTION
        "DNS list, should be valid unicast address."
    ::= { f3L3DhcpIPv4AddrPoolEntry 7 }

f3L3DhcpIPv4AddrPoolTotalCount OBJECT-TYPE
    SYNTAX      Unsigned32 
    MAX-ACCESS  read-only
    STATUS      current
    DESCRIPTION
        "The number of address available in the pool. min
        (number in pool range - number in excluded list –
        1(address of the  interface), system host supporting
        limit)."
    ::= { f3L3DhcpIPv4AddrPoolEntry 8 }

f3L3DhcpIPv4AddrPoolAllocatedCount OBJECT-TYPE
    SYNTAX      Unsigned32 
    MAX-ACCESS  read-only
    STATUS      current
    DESCRIPTION
        "The number of address is allocated."
    ::= { f3L3DhcpIPv4AddrPoolEntry 9 }

f3L3DhcpIPv4AddrPoolAction OBJECT-TYPE
    SYNTAX      DhcpIPv4AddrPoolActionType 
    MAX-ACCESS  read-create
    STATUS      current
    DESCRIPTION
        "Action of Dhcp IPv4 Address Pool."
    ::= { f3L3DhcpIPv4AddrPoolEntry 10 }

f3L3DhcpIPv4AddrPoolActionIPv4Addr OBJECT-TYPE
    SYNTAX      IpAddress 
    MAX-ACCESS  read-create
    STATUS      current
    DESCRIPTION
        "IPv4 Address of Action."
    ::= { f3L3DhcpIPv4AddrPoolEntry 11 }

f3L3DhcpIPv4AddrPoolStorageType OBJECT-TYPE
    SYNTAX      StorageType 
    MAX-ACCESS  read-create
    STATUS      current
    DESCRIPTION
        "The type of storage configured for this entry."
    ::= { f3L3DhcpIPv4AddrPoolEntry 12 }

f3L3DhcpIPv4AddrPoolRowStatus OBJECT-TYPE
    SYNTAX      RowStatus 
    MAX-ACCESS  read-create
    STATUS      current
    DESCRIPTION
        "The status of this row. The object may be modified
        if the associated instance of this object is equal
        to active(1), notInService(2), or notReady(3)."
    ::= { f3L3DhcpIPv4AddrPoolEntry 13 }

--
-- L3 Dhcp Excluded IPv4 Addr List Table
--
f3L3DhcpExcludedIPv4AddrListTable  OBJECT-TYPE
    SYNTAX      SEQUENCE OF F3L3DhcpExcludedIPv4AddrListEntry
    MAX-ACCESS  not-accessible
    STATUS      current
    DESCRIPTION
        "A list of L3 Dhcp Excluded IPv4 Addr List fsp150 family of products."
    ::= { f3L3Objects 57 }

f3L3DhcpExcludedIPv4AddrListEntry  OBJECT-TYPE
    SYNTAX      F3L3DhcpExcludedIPv4AddrListEntry
    MAX-ACCESS  not-accessible
    STATUS      current
    DESCRIPTION
        "A conceptual row in the f3L3DhcpExcludedIPv4AddrListTable. Entries can
        be created/deleted in this table by management application action."
    INDEX { neIndex,
            shelfIndex,
            slotIndex,
            f3L3FlowPointPortIndex,
            f3L3FlowPointIndex,
            f3L3TrafficIPIfIndex,
            f3L3DhcpIPv4AddrPoolIndex,
            f3L3DhcpExcludedIPv4AddrListStartAddr }
    ::= { f3L3DhcpExcludedIPv4AddrListTable 1 }

F3L3DhcpExcludedIPv4AddrListEntry ::= SEQUENCE {
      f3L3DhcpExcludedIPv4AddrListStartAddr      IpAddress,
      f3L3DhcpExcludedIPv4AddrListEndAddr        IpAddress,
      f3L3DhcpExcludedIPv4AddrListStorageType    StorageType,
      f3L3DhcpExcludedIPv4AddrListRowStatus      RowStatus
    }

f3L3DhcpExcludedIPv4AddrListStartAddr OBJECT-TYPE
    SYNTAX      IpAddress 
    MAX-ACCESS  not-accessible
    STATUS      current
    DESCRIPTION
        "A unique index value used to uniquely identify a entry."
    ::= { f3L3DhcpExcludedIPv4AddrListEntry 1 }

f3L3DhcpExcludedIPv4AddrListEndAddr OBJECT-TYPE
    SYNTAX      IpAddress 
    MAX-ACCESS  read-create
    STATUS      current
    DESCRIPTION
        "The end IP address."
    ::= { f3L3DhcpExcludedIPv4AddrListEntry 2 }

f3L3DhcpExcludedIPv4AddrListStorageType OBJECT-TYPE
    SYNTAX      StorageType 
    MAX-ACCESS  read-create
    STATUS      current
    DESCRIPTION
        "The type of storage configured for this entry."
    ::= { f3L3DhcpExcludedIPv4AddrListEntry 3 }

f3L3DhcpExcludedIPv4AddrListRowStatus OBJECT-TYPE
    SYNTAX      RowStatus 
    MAX-ACCESS  read-create
    STATUS      current
    DESCRIPTION
        "The status of this row. The object may be modified
        if the associated instance of this object is equal
        to active(1), notInService(2), or notReady(3)."
    ::= { f3L3DhcpExcludedIPv4AddrListEntry 4 }

--
-- L3 Dhcp Static Binding IPv4 Addr Table
--
f3L3DhcpStaticBindingIPv4AddrTable  OBJECT-TYPE
    SYNTAX      SEQUENCE OF F3L3DhcpStaticBindingIPv4AddrEntry
    MAX-ACCESS  not-accessible
    STATUS      current
    DESCRIPTION
        "A list of L3 Dhcp Static Binding IPv4 Addr fsp150 family of products."
    ::= { f3L3Objects 58 }

f3L3DhcpStaticBindingIPv4AddrEntry  OBJECT-TYPE
    SYNTAX      F3L3DhcpStaticBindingIPv4AddrEntry
    MAX-ACCESS  not-accessible
    STATUS      current
    DESCRIPTION
        "A conceptual row in the f3L3DhcpStaticBindingIPv4AddrTable. Entries can
        be created/deleted in this table by management application action."
    INDEX { neIndex,
            shelfIndex,
            slotIndex,
            f3L3FlowPointPortIndex,
            f3L3FlowPointIndex,
            f3L3TrafficIPIfIndex,
            f3L3DhcpIPv4AddrPoolIndex,
            f3L3DhcpStaticBindingIPv4AddrIpAddr }
    ::= { f3L3DhcpStaticBindingIPv4AddrTable 1 }

F3L3DhcpStaticBindingIPv4AddrEntry ::= SEQUENCE {
      f3L3DhcpStaticBindingIPv4AddrIpAddr         IpAddress,
      f3L3DhcpStaticBindingIPv4AddrBindType       DhcpIpAddrBindType,
      f3L3DhcpStaticBindingIPv4AddrLeaseTime      Unsigned32,
      f3L3DhcpStaticBindingIPv4AddrValue          DisplayString,
      f3L3DhcpStaticBindingIPv4AddrStorageType    StorageType,
      f3L3DhcpStaticBindingIPv4AddrRowStatus      RowStatus
    }

f3L3DhcpStaticBindingIPv4AddrIpAddr OBJECT-TYPE
    SYNTAX      IpAddress 
    MAX-ACCESS  not-accessible
    STATUS      current
    DESCRIPTION
        "A unique index value used to uniquely identify a entry."
    ::= { f3L3DhcpStaticBindingIPv4AddrEntry 1 }

f3L3DhcpStaticBindingIPv4AddrBindType OBJECT-TYPE
    SYNTAX      DhcpIpAddrBindType 
    MAX-ACCESS  read-create
    STATUS      current
    DESCRIPTION
        "Indicate to bind the address to source MAC address
        or Client-ID from received packet."
    ::= { f3L3DhcpStaticBindingIPv4AddrEntry 2 }

f3L3DhcpStaticBindingIPv4AddrLeaseTime OBJECT-TYPE
    SYNTAX      Unsigned32 
    MAX-ACCESS  read-create
    STATUS      current
    DESCRIPTION
        "The time in seconds, from 120 to 31536000 (365
        days),0xffffffff means infinite."
    ::= { f3L3DhcpStaticBindingIPv4AddrEntry 3 }

f3L3DhcpStaticBindingIPv4AddrValue OBJECT-TYPE
    SYNTAX      DisplayString
    MAX-ACCESS  read-create
    STATUS      current
    DESCRIPTION
        "The value of MAC address or Client ID string to be
        compared.When type is MAC address or Client-ID-MAC,
        should be in MAC address format (xx:xx:xx:xx:xx:xx)."
    ::= { f3L3DhcpStaticBindingIPv4AddrEntry 4 }

f3L3DhcpStaticBindingIPv4AddrStorageType OBJECT-TYPE
    SYNTAX      StorageType 
    MAX-ACCESS  read-create
    STATUS      current
    DESCRIPTION
        "The type of storage configured for this entry."
    ::= { f3L3DhcpStaticBindingIPv4AddrEntry 5 }

f3L3DhcpStaticBindingIPv4AddrRowStatus OBJECT-TYPE
    SYNTAX      RowStatus 
    MAX-ACCESS  read-create
    STATUS      current
    DESCRIPTION
        "The status of this row. The object may be modified
        if the associated instance of this object is equal
        to active(1), notInService(2), or notReady(3)."
    ::= { f3L3DhcpStaticBindingIPv4AddrEntry 6 }

--
-- L3 Dhcp Active Lease IPv4 Addr Table
--
f3L3DhcpActiveLeaseIPv4AddrTable  OBJECT-TYPE
    SYNTAX      SEQUENCE OF F3L3DhcpActiveLeaseIPv4AddrEntry
    MAX-ACCESS  not-accessible
    STATUS      current
    DESCRIPTION
        "A list of L3 Dhcp Active Lease IPv4 Addr fsp150 family of products."
    ::= { f3L3Objects 59 }

f3L3DhcpActiveLeaseIPv4AddrEntry  OBJECT-TYPE
    SYNTAX      F3L3DhcpActiveLeaseIPv4AddrEntry
    MAX-ACCESS  not-accessible
    STATUS      current
    DESCRIPTION
        "A conceptual row in the f3L3DhcpActiveLeaseIPv4AddrTable. Entries can
        be created/deleted in this table by management application action."
    INDEX { neIndex,
            shelfIndex,
            slotIndex,
            f3L3FlowPointPortIndex,
            f3L3FlowPointIndex,
            f3L3TrafficIPIfIndex,
            f3L3DhcpIPv4AddrPoolIndex,
            f3L3DhcpActiveLeaseIPv4AddrIpAddr }
    ::= { f3L3DhcpActiveLeaseIPv4AddrTable 1 }

F3L3DhcpActiveLeaseIPv4AddrEntry ::= SEQUENCE {
      f3L3DhcpActiveLeaseIPv4AddrIpAddr           IpAddress,
      f3L3DhcpActiveLeaseIPv4AddrVendorClassId    DisplayString,
      f3L3DhcpActiveLeaseIPv4AddrLeaseTime        Unsigned32,
      f3L3DhcpActiveLeaseIPv4AddrExpireTime       Unsigned32,
      f3L3DhcpActiveLeaseIPv4AddrMacAddr          MacAddress,
      f3L3DhcpActiveLeaseIPv4AddrClientId         DisplayString
    }

f3L3DhcpActiveLeaseIPv4AddrIpAddr OBJECT-TYPE
    SYNTAX      IpAddress 
    MAX-ACCESS  not-accessible
    STATUS      current
    DESCRIPTION
        "A unique index value used to uniquely identify a entry."
    ::= { f3L3DhcpActiveLeaseIPv4AddrEntry 1 }

f3L3DhcpActiveLeaseIPv4AddrVendorClassId OBJECT-TYPE
    SYNTAX      DisplayString
    MAX-ACCESS  read-only
    STATUS      current
    DESCRIPTION
        "Vendor Class-ID of the host."
    ::= { f3L3DhcpActiveLeaseIPv4AddrEntry 2 }

f3L3DhcpActiveLeaseIPv4AddrLeaseTime OBJECT-TYPE
    SYNTAX      Unsigned32 
    MAX-ACCESS  read-only
    STATUS      current
    DESCRIPTION
        "The time in seconds, from 120 to 31536000 (365
        days),0xffffffff means infinite."
    ::= { f3L3DhcpActiveLeaseIPv4AddrEntry 3 }

f3L3DhcpActiveLeaseIPv4AddrExpireTime OBJECT-TYPE
    SYNTAX      Unsigned32 
    MAX-ACCESS  read-only
    STATUS      current
    DESCRIPTION
        "The Expire time of the lease."
    ::= { f3L3DhcpActiveLeaseIPv4AddrEntry 4 }

f3L3DhcpActiveLeaseIPv4AddrMacAddr OBJECT-TYPE
    SYNTAX      MacAddress 
    MAX-ACCESS  read-only
    STATUS      current
    DESCRIPTION
        "MAC address of the host."
    ::= { f3L3DhcpActiveLeaseIPv4AddrEntry 5 }

f3L3DhcpActiveLeaseIPv4AddrClientId OBJECT-TYPE
    SYNTAX      DisplayString
    MAX-ACCESS  read-only
    STATUS      current
    DESCRIPTION
        "Client-ID of the host."
    ::= { f3L3DhcpActiveLeaseIPv4AddrEntry 6 }

---
---Notifications
---
f3L3FlowPointThresholdCrossingAlert NOTIFICATION-TYPE
    OBJECTS {
                f3L3FlowPointThresholdIndex,       
                f3L3FlowPointThresholdInterval,
                f3L3FlowPointThresholdVariable,
                f3L3FlowPointThresholdValueLo,
                f3L3FlowPointThresholdValueHi,
                f3L3FlowPointThresholdMonValue
            }
    STATUS  current
    DESCRIPTION
            "This trap is sent each time a threshold on a PM condition
             on an L3 flow point is crossed."
  ::= { f3L3Notifications 1 }

f3L3QosPolicerThresholdCrossingAlert NOTIFICATION-TYPE
    OBJECTS {
                f3L3QosPolicerThresholdIndex,       
                f3L3QosPolicerThresholdInterval,
                f3L3QosPolicerThresholdVariable,
                f3L3QosPolicerThresholdValueLo,
                f3L3QosPolicerThresholdValueHi,
                f3L3QosPolicerThresholdMonValue
            }
    STATUS  current
    DESCRIPTION
            "This trap is sent each time a threshold on a PM condition
             on an L3 Qos Policer is crossed."
  ::= { f3L3Notifications 2 }

f3L3QosShaperThresholdCrossingAlert NOTIFICATION-TYPE
    OBJECTS {
                f3L3QosShaperThresholdIndex,       
                f3L3QosShaperThresholdInterval,
                f3L3QosShaperThresholdVariable,
                f3L3QosShaperThresholdValueLo,
                f3L3QosShaperThresholdValueHi,
                f3L3QosShaperThresholdMonValue
            }
    STATUS  current
    DESCRIPTION
            "This trap is sent each time a threshold on a PM condition
             on an L3 Qos Shaper is crossed."
  ::= { f3L3Notifications 3 }

f3L3TrafficIpInterfaceThresholdCrossingAlert NOTIFICATION-TYPE
    OBJECTS {
                f3L3TrafficIpInterfaceThresholdIndex,       
                f3L3TrafficIpInterfaceThresholdInterval,
                f3L3TrafficIpInterfaceThresholdVariable,
                f3L3TrafficIpInterfaceThresholdValueLo,
                f3L3TrafficIpInterfaceThresholdValueHi,
                f3L3TrafficIpInterfaceThresholdMonValue
            }
    STATUS  current
    DESCRIPTION
            "This trap is sent each time a threshold on a PM condition
             on an L3 traffic ip interface is crossed."
  ::= { f3L3Notifications 4 }

f3L3AclRuleThresholdCrossingAlert NOTIFICATION-TYPE
    OBJECTS {
                f3L3AclRuleThresholdIndex,       
                f3L3AclRuleThresholdInterval,
                f3L3AclRuleThresholdVariable,
                f3L3AclRuleThresholdValueLo,
                f3L3AclRuleThresholdValueHi,
                f3L3AclRuleThresholdMonValue
            }
    STATUS  current
    DESCRIPTION
            "This trap is sent each time a threshold on a PM condition
             on an L3 acl rule is crossed."
  ::= { f3L3Notifications 5 }

f3L2A2NAclRuleThresholdCrossingAlert NOTIFICATION-TYPE
    OBJECTS {
                f3L2A2NAclRuleThresholdIndex,       
                f3L2A2NAclRuleThresholdInterval,
                f3L2A2NAclRuleThresholdVariable,
                f3L2A2NAclRuleThresholdValueLo,
                f3L2A2NAclRuleThresholdValueHi,
                f3L2A2NAclRuleThresholdMonValue
            }
    STATUS  current
    DESCRIPTION
            "This trap is sent each time a threshold on a PM condition
             on an L2 A2N acl rule is crossed."
  ::= { f3L3Notifications 6 }

f3L2N2AAclRuleThresholdCrossingAlert NOTIFICATION-TYPE
    OBJECTS {
                f3L2N2AAclRuleThresholdIndex,       
                f3L2N2AAclRuleThresholdInterval,
                f3L2N2AAclRuleThresholdVariable,
                f3L2N2AAclRuleThresholdValueLo,
                f3L2N2AAclRuleThresholdValueHi,
                f3L2N2AAclRuleThresholdMonValue
            }
    STATUS  current
    DESCRIPTION
            "This trap is sent each time a threshold on a PM condition
             on an L2 N2A acl rule is crossed."
  ::= { f3L3Notifications 7 }

f3L3TrafficIPv6InterfaceThresholdCrossingAlert NOTIFICATION-TYPE
    OBJECTS {
                f3L3TrafficIPv6InterfaceThresholdIndex,       
                f3L3TrafficIPv6InterfaceThresholdInterval,
                f3L3TrafficIPv6InterfaceThresholdVariable,
                f3L3TrafficIPv6InterfaceThresholdValueLo,
                f3L3TrafficIPv6InterfaceThresholdValueHi,
                f3L3TrafficIPv6InterfaceThresholdMonValue
            }
    STATUS  current
    DESCRIPTION
            "This trap is sent each time a threshold on a PM condition
             on an L3 traffic ipv6 interface is crossed."
  ::= { f3L3Notifications 8 }

cmL3FlowPointThresholdCrossingAlert NOTIFICATION-TYPE
    OBJECTS {
                cmL3FlowPointThresholdIndex,       
                cmL3FlowPointThresholdInterval,
                cmL3FlowPointThresholdVariable,
                cmL3FlowPointThresholdValueLo,
                cmL3FlowPointThresholdValueHi,
                cmL3FlowPointThresholdMonValue
            }
    STATUS  current
    DESCRIPTION
            "This trap is sent each time a threshold on a PM condition
             on an L3 flow point is crossed."
  ::= { cmL3Notifications 9 }


cmL3QosPolicerThresholdCrossingAlert NOTIFICATION-TYPE
    OBJECTS {
                cmL3QosPolicerThresholdIndex,       
                cmL3QosPolicerThresholdInterval,
                cmL3QosPolicerThresholdVariable,
                cmL3QosPolicerThresholdValueLo,
                cmL3QosPolicerThresholdValueHi,
                cmL3QosPolicerThresholdMonValue
            }
    STATUS  current
    DESCRIPTION
            "This trap is sent each time a threshold on a PM condition
             on an L3 Qos Policer is crossed."
  ::= { cmL3Notifications 10 }

cmL3QosShaperThresholdCrossingAlert NOTIFICATION-TYPE
    OBJECTS {
                cmL3QosShaperThresholdIndex,       
                cmL3QosShaperThresholdInterval,
                cmL3QosShaperThresholdVariable,
                cmL3QosShaperThresholdValueLo,
                cmL3QosShaperThresholdValueHi,
                cmL3QosShaperThresholdMonValue
            }
    STATUS  current
    DESCRIPTION
            "This trap is sent each time a threshold on a PM condition
             on an L3 Qos Shaper is crossed."
  ::= { cmL3Notifications 11 }

--
-- Conformance
--
f3L3Compliances OBJECT IDENTIFIER ::= {f3L3Conformance 1}
f3L3Groups      OBJECT IDENTIFIER ::= {f3L3Conformance 2}

f3L3Compliance MODULE-COMPLIANCE
    STATUS  current
    DESCRIPTION
            "Describes the requirements for conformance to the L3."
    MODULE  -- this module
        MANDATORY-GROUPS {
              f3L3ObjectsGroup, f3L3PerfGroup, f3L3TrafficOspfGroup, 
              f3L3TrafficIPv6Group, f3L3TrafficBgpGroup, f3L3DhcpGroup
        }
    ::= { f3L3Compliances 1 }

f3L3ObjectsGroup OBJECT-GROUP
    OBJECTS {
        f3DhcpRelayAgentIndex,f3DhcpRelayAgentAlias,f3DhcpRelayAgentAdminState,
        f3DhcpRelayAgentSecondaryState,f3DhcpRelayAgentOperationalState,
        f3DhcpRelayAgentIpVersion,f3DhcpRelayAgentServerIpAddress,
        f3DhcpRelayAgentOp82SubOp9ControlEnabled,f3DhcpRelayAgentOp82SubOp9Value,
        f3DhcpRelayAgentStorageType, f3DhcpRelayAgentRowStatus,
        f3DhcpRelayAgentServerIpAddressList,
    
        f3VrfIndex,f3VrfAlias, f3VrfAdminState,f3VrfSecondaryState,f3VrfTraceRouteIpv4Destination,
        f3VrfOperationalState,f3VrfAccIsolationControlEnabled,f3VrfPingResult,f3VrfPingIpv4Destination,
        f3VrfTraceRouteResult,f3VrfAction,f3VrfStorageType,f3VrfTransportType,f3VrfRowStatus,f3VrfDhcpRoutesControl,
        f3VrfActionX,f3VrfActionIfName,f3VrfIpVersion,f3VrfPingIpv6Destination,f3VrfTraceRouteIpv6Destination,

        f3L3FlowPointPortTypeIndex,f3L3FlowPointPortIndex,
        f3L3FlowPointIndex,f3L3FlowPointAlias,f3L3FlowPointAdminState,f3L3FlowPointSecondaryState,
        f3L3FlowPointOperationalState,f3L3FlowPointMultiCOSEnabled,f3L3FlowPointCOS,f3L3FlowPointUntaggedMemberShipEnabled,
        f3L3FlowPointOuterTagMemberShipEnabled,f3L3FlowPointOuterTagMemberShipVlanId,
        f3L3FlowPointInnerTagMemberShipEnabled,f3L3FlowPointInnerTagMemberShipVlanId,
        f3L3FlowPointFragmentedPktsFwdEnabled,
        f3L3FlowPointHCosMgmtEnabled,f3L3FlowPointHCosGuaranteedBwHi,f3L3FlowPointHCosGuaranteedBwLo,
        f3L3FlowPointHCosMaximumBwHi,f3L3FlowPointHCosMaximumBwLo,f3L3FlowPointPolicingEnabled,
        f3L3FlowPointStorageType,f3L3FlowPointRowStatus,
        f3L3FlowPointDscpOverwriteControl,
        f3L3FlowPointPriMapProfile,f3L3FlowPointRefConnectGuardFlow,
        f3L3FlowPointSecureState,f3L3FlowPointSecureBlockingEnabled,
        f3L3FlowPointWfqSegmentationCOS,
        f3L3FlowPointWfqGroupCOS,
        f3L3FlowPointWfqGroupEirLo,
        f3L3FlowPointWfqGroupEirHi,
        f3L3FlowPointOuterVlanEthertype,
        f3L3FlowPointInnerVlanEthertype,
        f3L3FlowPointIpVersion,

        f3L3AclRuleParentIndex,f3L3AclRuleIndex,f3L3AclRuleAlias,f3L3AclRuleSrcIpv4AddressControl,
        f3L3AclRuleDynamicSrcIpControl,f3L3AclRuleSrcIpv4AddressLowLimit,f3L3AclRuleDstIpv4AddressControl,
        f3L3AclRuleDstIpv4AddressLowLimit,f3L3AclRuleIpv4PriorityControl,f3L3AclRuleIpv4PriorityLowLimit,
        f3L3AclRuleProtocolControl,f3L3AclRuleProtocolNumber,f3L3AclRuleSrcPortControl,
        f3L3AclRuleSrcPortLowLimit,f3L3AclRuleSrcPortHighLimit,f3L3AclRuleDstPortControl,
        f3L3AclRuleDstPortLowLimit,f3L3AclRuleDstPortHighLimit,f3L3AclRulePriority,f3L3AclRuleCOS,
        f3L3AclRuleOperation,f3L3AclRuleSummary,f3L3AclRuleCosOverrideControl,
        f3L3AclRuleSrcMacAddressControl,f3L3AclRuleDynamicSrcMacAddressControl,
        f3L3AclRuleSrcMacAddress,f3L3AclRuleSrcMacAddressMask,f3L3AclRuleDstMacAddressControl,
        f3L3AclRuleDstMacAddress,f3L3AclRuleDstMacAddressMask,f3L3AclRuleOuterVlanVIDControl,
        f3L3AclRuleOuterVlanVIDLowLimit,f3L3AclRuleOuterVlanVIDHighLimit,
        f3L3AclRuleInnerVlanVIDControl,f3L3AclRuleInnerVlanVIDLowLimit,f3L3AclRuleInnerVlanVIDHighLimit,
        f3L3AclRuleOuterVlanPcpControl,f3L3AclRuleOuterVlanPcpLowLimit,f3L3AclRuleOuterVlanPcpHighLimit,
        f3L3AclRuleInnerVlanPcpControl,f3L3AclRuleInnerVlanPcpLowLimit,f3L3AclRuleInnerVlanPcpHighLimit,
        f3L3AclRuleOuterVlanDeiControl,f3L3AclRuleOuterVlanDei,f3L3AclRuleEtherTypeControl,
        f3L3AclRuleEtherType,f3L3AclRuleTcpFlagsControl,f3L3AclRuleTcpFlags,
        f3L3AclRuleSrcIpv4AddressHighLimit,f3L3AclRuleDstIpv4AddressHighLimit,f3L3AclRuleIpv4PriorityHighLimit,
        f3L3AclRuleStorageType,f3L3AclRuleRowStatus,f3L3AclRuleAdminState,
        f3L3AclRuleActive,f3L3AclRuleSrcIpV6AddressControl,f3L3AclRuleSrcIpV6Address,
        f3L3AclRuleSrcIpV6AddressPrefixLen,f3L3AclRuleDstIpV6AddressControl,f3L3AclRuleDstIpV6Address,
        f3L3AclRuleDstIpV6AddressPrefixLen,f3L3AclRuleIpV6FlowLabelControl,f3L3AclRuleIpV6FlowLabel,
        f3L3AclRuleIpV6FlowLabel, f3L3AclRulePriorityControl, f3L3AclRulePriorityLowLimit, 
        f3L3AclRulePriorityHighLimit,

        f3L2A2NAclRuleParentIndex,f3L2A2NAclRuleIndex,f3L2A2NAclRuleAlias,f3L2A2NAclRuleSrcIpv4AddressControl,
        f3L2A2NAclRuleDynamicSrcIpControl,f3L2A2NAclRuleSrcIpv4AddressLowLimit,f3L2A2NAclRuleDstIpv4AddressControl,
        f3L2A2NAclRuleDstIpv4AddressLowLimit,f3L2A2NAclRuleIpv4PriorityControl,f3L2A2NAclRuleIpv4PriorityLowLimit,
        f3L2A2NAclRuleProtocolControl,f3L2A2NAclRuleProtocolNumber,f3L2A2NAclRuleSrcPortControl,f3L2A2NAclRuleSrcPortLowLimit,
        f3L2A2NAclRuleSrcPortHighLimit,f3L2A2NAclRuleDstPortControl,f3L2A2NAclRuleDstPortLowLimit,f3L2A2NAclRuleDstPortHighLimit,
        f3L2A2NAclRulePriority,f3L2A2NAclRuleCOS,f3L2A2NAclRuleOperation,f3L2A2NAclRuleSummary,f3L2A2NAclRuleCosOverrideControl,
        f3L2A2NAclRuleSrcMacAddressControl,f3L2A2NAclRuleDynamicSrcMacAddressControl,f3L2A2NAclRuleSrcMacAddress,
        f3L2A2NAclRuleSrcMacAddressMask,f3L2A2NAclRuleDstMacAddressControl,f3L2A2NAclRuleDstMacAddress,f3L2A2NAclRuleDstMacAddressMask,
        f3L2A2NAclRuleOuterVlanVIDControl,f3L2A2NAclRuleOuterVlanVIDLowLimit,f3L2A2NAclRuleOuterVlanVIDHighLimit,f3L2A2NAclRuleInnerVlanVIDControl,
        f3L2A2NAclRuleInnerVlanVIDLowLimit,f3L2A2NAclRuleInnerVlanVIDHighLimit,f3L2A2NAclRuleOuterVlanPcpControl,f3L2A2NAclRuleOuterVlanPcpLowLimit,
        f3L2A2NAclRuleOuterVlanPcpHighLimit,f3L2A2NAclRuleInnerVlanPcpControl,f3L2A2NAclRuleInnerVlanPcpLowLimit,f3L2A2NAclRuleInnerVlanPcpHighLimit,
        f3L2A2NAclRuleOuterVlanDeiControl,f3L2A2NAclRuleOuterVlanDei,f3L2A2NAclRuleEtherTypeControl,f3L2A2NAclRuleEtherType,
        f3L2A2NAclRuleTcpFlagsControl,f3L2A2NAclRuleTcpFlags,f3L2A2NAclRuleSrcIpv4AddressHighLimit,f3L2A2NAclRuleDstIpv4AddressHighLimit,
        f3L2A2NAclRuleIpv4PriorityHighLimit,f3L2A2NAclRuleStorageType,f3L2A2NAclRuleRowStatus,f3L2A2NAclRuleAdminState,
        f3L2A2NAclRuleActive,f3L2A2NAclRuleSrcIpV6AddressControl,f3L2A2NAclRuleSrcIpV6Address,f3L2A2NAclRuleSrcIpV6AddressPrefixLen,
        f3L2A2NAclRuleDstIpV6AddressControl,f3L2A2NAclRuleDstIpV6Address,f3L2A2NAclRuleDstIpV6AddressPrefixLen,
        f3L2A2NAclRuleIpV6FlowLabelControl,f3L2A2NAclRuleIpV6FlowLabel,

        f3L2N2AAclRuleParentIndex,f3L2N2AAclRuleIndex,f3L2N2AAclRuleAlias,f3L2N2AAclRuleSrcIpv4AddressControl,
        f3L2N2AAclRuleDynamicSrcIpControl,f3L2N2AAclRuleSrcIpv4AddressLowLimit,f3L2N2AAclRuleDstIpv4AddressControl,
        f3L2N2AAclRuleDstIpv4AddressLowLimit,f3L2N2AAclRuleIpv4PriorityControl,f3L2N2AAclRuleIpv4PriorityLowLimit,
        f3L2N2AAclRuleProtocolControl,f3L2N2AAclRuleProtocolNumber,f3L2N2AAclRuleSrcPortControl,f3L2N2AAclRuleSrcPortLowLimit,
        f3L2N2AAclRuleSrcPortHighLimit,f3L2N2AAclRuleDstPortControl,f3L2N2AAclRuleDstPortLowLimit,f3L2N2AAclRuleDstPortHighLimit,
        f3L2N2AAclRulePriority,f3L2N2AAclRuleCOS,f3L2N2AAclRuleOperation,f3L2N2AAclRuleSummary,f3L2N2AAclRuleCosOverrideControl,
        f3L2N2AAclRuleSrcMacAddressControl,f3L2N2AAclRuleDynamicSrcMacAddressControl,f3L2N2AAclRuleSrcMacAddress,
        f3L2N2AAclRuleSrcMacAddressMask,f3L2N2AAclRuleDstMacAddressControl,f3L2N2AAclRuleDstMacAddress,f3L2N2AAclRuleDstMacAddressMask,
        f3L2N2AAclRuleOuterVlanVIDControl,f3L2N2AAclRuleOuterVlanVIDLowLimit,f3L2N2AAclRuleOuterVlanVIDHighLimit,f3L2N2AAclRuleInnerVlanVIDControl,
        f3L2N2AAclRuleInnerVlanVIDLowLimit,f3L2N2AAclRuleInnerVlanVIDHighLimit,f3L2N2AAclRuleOuterVlanPcpControl,f3L2N2AAclRuleOuterVlanPcpLowLimit,
        f3L2N2AAclRuleOuterVlanPcpHighLimit,f3L2N2AAclRuleInnerVlanPcpControl,f3L2N2AAclRuleInnerVlanPcpLowLimit,f3L2N2AAclRuleInnerVlanPcpHighLimit,
        f3L2N2AAclRuleOuterVlanDeiControl,f3L2N2AAclRuleOuterVlanDei,f3L2N2AAclRuleEtherTypeControl,f3L2N2AAclRuleEtherType,
        f3L2N2AAclRuleTcpFlagsControl,f3L2N2AAclRuleTcpFlags,f3L2N2AAclRuleSrcIpv4AddressHighLimit,f3L2N2AAclRuleDstIpv4AddressHighLimit,
        f3L2N2AAclRuleIpv4PriorityHighLimit,f3L2N2AAclRuleStorageType,f3L2N2AAclRuleRowStatus,f3L2N2AAclRuleAdminState,
        f3L2N2AAclRuleActive,f3L2N2AAclRuleSrcIpV6AddressControl,f3L2N2AAclRuleSrcIpV6Address,f3L2N2AAclRuleSrcIpV6AddressPrefixLen,
        f3L2N2AAclRuleDstIpV6AddressControl,f3L2N2AAclRuleDstIpV6Address,f3L2N2AAclRuleDstIpV6AddressPrefixLen,
        f3L3AclRuleIpV6FlowLabelControl,f3L3AclRuleIpV6FlowLabel,

        f3L3QosPolicerIndex,f3L3QosPolicerAdminState,f3L3QosPolicerOperationalState,
        f3L3QosPolicerSecondaryState,f3L3QosPolicerCIRLo,f3L3QosPolicerCIRHi,f3L3QosPolicerEIRLo,
        f3L3QosPolicerEIRHi,f3L3QosPolicerCBS,f3L3QosPolicerEBS,f3L3QosPolicerAlgorithm,
        f3L3QosPolicerColorMode,f3L3QosPolicerCouplingFlag,
        f3L3QosPolicerStorageType,f3L3QosPolicerRowStatus,
        f3L3QosPolicerCIRMaxHi,
        f3L3QosPolicerCIRMaxLo,
        f3L3QosPolicerEIRMaxHi,
        f3L3QosPolicerEIRMaxLo,
        f3L3QosPolicerEnvelopeObject,
        f3L3QosPolicerRank,
        f3L3QosPolicerPolicingEnabled,

        f3L3QosShaperIndex,f3L3QosShaperAdminState,f3L3QosShaperOperationalState,
        f3L3QosShaperSecondaryState,f3L3QosShaperCIRLo,f3L3QosShaperCIRHi,f3L3QosShaperEIRLo,
        f3L3QosShaperEIRHi,f3L3QosShaperBufferSize,f3L3QosShaperCOS,
        f3L3QosShaperWredGreenMinQueueThreshold,f3L3QosShaperWredGreenMaxQueueThreshold,
        f3L3QosShaperWredGreenDropProbability,f3L3QosShaperWredYellowMinQueueThreshold,f3L3QosShaperWredYellowMaxQueueThreshold,
        f3L3QosShaperWredYellowDropProbability,f3L3QosShaperStorageType,f3L3QosShaperRowStatus,
        f3L3QosShaperWfqWeight,

        f3L3TrafficIPIfIndex,f3L3TrafficIPIfName,f3L3TrafficIPIfAdminState,f3L3TrafficIPIfSecondaryState,
        f3L3TrafficIPIfOperationalState,f3L3TrafficIPIfProxyArpEnabled,f3L3TrafficIPIfIpAddressSourceType,
        f3L3TrafficIPIfMgmtUseEnable,f3L3TrafficIPIfIpAddress,f3L3TrafficIPIfMask,
        f3L3TrafficIPIfDhcpRelayInterfaceSide,f3L3TrafficIPIfDhcpRelayVendorClassiDOpt60,
        f3L3TrafficIPIfDhcpRelayVendorClassiDOpt60Control,f3L3TrafficIPIfDhcpRelayUserClassOpt77,
        f3L3TrafficIPIfDhcpRelayInfoOpt82Sub1,f3L3TrafficIPIfDhcpRelayUserClassOpt77Control,
        f3L3TrafficIPIfDhcpRelayInfoOpt82Sub1Enabled,f3L3TrafficIPIfDhcpRelayInfoOpt82Sub2,
        f3L3TrafficIPIfDhcpRelayInfoOpt82Sub2Enabled,f3L3TrafficIPIfDhcpEnabled,f3L3TrafficIPIfDhcpRole,
        f3L3TrafficIPIfDhcpClientIdEnabled,f3L3TrafficIPIfDhcpClientId,f3L3TrafficIPIfDhcpClassIdEnabled,
        f3L3TrafficIPIfDhcpHostNameEnabled,f3L3TrafficIPIfDhcpHostName,
        f3L3TrafficIPIfDhcpClientIdType,f3L3TrafficIPIfDhcpHostNameType,
        f3L3TrafficIPIfStorageType,f3L3TrafficIPIfRowStatus,f3L3TrafficIPIfAction, f3L3TrafficIPIfActionX,
        f3L3TrafficIPIfUnnumberedControl,f3L3TrafficIPIfBorrowedIntf,
        f3L3TrafficIPIfIpMode,f3L3TrafficIPIfType,f3L3TrafficIPIfIpv6LinkLocalAddr,
        f3L3TrafficIPIfIpv6LinkLocalAddrMode,f3L3TrafficIPIfIpv6StatelessAddrAutoconfigEnabled,
        f3L3TrafficIPIfDefaultGateway,f3L3TrafficIPIfIcmpErrorMsgRateLimit,
        f3L3TrafficIPIfDhcpv6Role,f3L3TrafficIPIfDhcpv6Enabled,
        f3L3TrafficIPIfDhcpRapidCommitControlEnabled,f3L3TrafficIPIfMaxRAInterval,
        f3L3TrafficIPIfMinRAInterval,f3L3TrafficIPIfRouterLifeTime,f3L3TrafficIPIfReachableTime,
        f3L3TrafficIPIfRaDhcpMoreConfigEnabled,f3L3TrafficIPIfRaManagedAddressConfigEnabled,
        f3L3TrafficIPIfRaRDNSSOptionEnabled,f3L3TrafficIPIfRaRDNSSLifeTime,
        f3L3TrafficIPIfRaDNSSList,f3L3TrafficIPIfRaDefaultRouterPreference,
        f3L3TrafficIPIfDupAddrDetectControl,f3L3TrafficIPIfDupAddrDetectTransmits,
        f3L3TrafficIPIfDupAddrDetectRetransTimer,f3L3TrafficIPIfMTU,

        f3VrfActionIfName, f3VrfIpVersion, f3VrfPingIpv6Destination, f3VrfTraceRouteIpv6Destination,
        f3VrfMaxFwdTableEntries, f3VrfFwdTableFull, f3VrfEcmpDistribution,
        f3VrfEcmpStaticRoutesMaximumPaths,
        
        f3DhcpRelayAgentTrafficIpIfMemberObject,f3DhcpRelayAgentTrafficIpIfMemberStorageType,
        f3DhcpRelayAgentTrafficIpIfMemberRowStatus,
        
        f3VrfTrafficIpIfMemberObject,f3VrfTrafficIpIfMemberStorageType,f3VrfTrafficIpIfMemberRowStatus,

        f3L3TrafficIpv4RouteDest,
        f3L3TrafficIpv4RouteMask,f3L3TrafficIpv4RouteNextHop,f3L3TrafficIpv4RouteMetric,
        f3L3TrafficIpv4RouteInterface,f3L3TrafficIpv4RouteAdvertise,f3L3TrafficIpv4RouteStatus, f3L3TrafficIpv4RouteStatusX,
        f3L3TrafficIpv4RouteSourceForwardingEnable,f3L3TrafficIpv4RouteFlags,
        f3L3TrafficIpv4RouteStorageType,f3L3TrafficIpv4RouteRowStatus,f3L3TrafficIpv4RouteType,
        f3L3TrafficIpv4RouteStatusX,f3L3TrafficIpv4RouteOrigin,
        
        f3L3TrafficArpIPAddress, f3L3TrafficArpMacAddress, f3L3TrafficArpInterface,
        f3L3TrafficArpEntryType, f3L3TrafficArpStorageType,f3L3TrafficArpRowStatus,
        cmL3FlowPointPortIndex,  cmL3FlowPointIndex,       cmL3FlowPointAlias,
        cmL3FlowPointAdminState, cmL3FlowPointSecondaryState, cmL3FlowPointOperationalState,
        cmL3FlowPointMultiCOSEnabled, cmL3FlowPointCOS, cmL3FlowPointUntaggedMemberShipEnabled,
        cmL3FlowPointOuterTagMemberShipEnabled, cmL3FlowPointOuterTagMemberShipVlanId, cmL3FlowPointInnerTagMemberShipEnabled,
        cmL3FlowPointInnerTagMemberShipVlanId,  cmL3FlowPointFragmentedPktsFwdEnabled, cmL3FlowPointHCosMgmtEnabled,                    
        cmL3FlowPointHCosGuaranteedBwHi, cmL3FlowPointHCosGuaranteedBwLo, cmL3FlowPointHCosMaximumBwHi,                     
        cmL3FlowPointHCosMaximumBwLo, cmL3FlowPointDscpOverwriteControl,              
        cmL3FlowPointPriMapProfile,   cmL3FlowPointStorageType, cmL3FlowPointRowStatus, cmL3FlowPointAclNoMatchDisposition,
        cmL3FlowPointWfqSegmentationCOS, cmL3FlowPointWfqGroupCOS, cmL3FlowPointWfqGroupEirLo, cmL3FlowPointWfqGroupEirHi,
        cmL3FlowPointEgressShapingType,
        cmL3QosPolicerIndex, cmL3QosPolicerAdminState, cmL3QosPolicerOperationalState, 
        cmL3QosPolicerSecondaryState, cmL3QosPolicerCIRLo, cmL3QosPolicerCIRHi, cmL3QosPolicerEIRLo, 
        cmL3QosPolicerEIRHi, cmL3QosPolicerCBS, cmL3QosPolicerEBS, cmL3QosPolicerAlgorithm, 
        cmL3QosPolicerColorMode, cmL3QosPolicerCouplingFlag, cmL3QosPolicerCIRMaxHi, 
        cmL3QosPolicerCIRMaxLo, cmL3QosPolicerEIRMaxHi, cmL3QosPolicerEIRMaxLo, cmL3QosPolicerEnvelopeObject, 
        cmL3QosPolicerRank, cmL3QosPolicerPolicingEnabled, cmL3QosPolicerStorageType, cmL3QosPolicerRowStatus,
        cmL3QosShaperIndex, cmL3QosShaperAdminState, cmL3QosShaperOperationalState, 
        cmL3QosShaperSecondaryState, cmL3QosShaperCIRLo, cmL3QosShaperCIRHi, cmL3QosShaperEIRLo, 
        cmL3QosShaperEIRHi, cmL3QosShaperBufferSize, cmL3QosShaperCOS, cmL3QosShaperStorageType, cmL3QosShaperRowStatus,
        cmL3QosShaperWfqWeight,
        
        f3L3TrafficIpv4StaticRouteDest, f3L3TrafficIpv4StaticRouteMask, f3L3TrafficIpv4StaticRouteNextHop,
        f3L3TrafficIpv4StaticRouteInterface, f3L3TrafficIpv4StaticRouteMetric,
        f3L3TrafficIpv4StaticRouteSourceForwardingEnable, f3L3TrafficIpv4StaticRouteStorageType, 
        f3L3TrafficIpv4StaticRouteRowStatus,
        
        f3L3TrafficIpv4AllRouteDest, f3L3TrafficIpv4AllRouteMask, f3L3TrafficIpv4AllRouteNextHop,
        f3L3TrafficIpv4AllRouteInterface, f3L3TrafficIpv4AllRouteOrigin,
        f3L3TrafficIpv4AllRouteMetric, f3L3TrafficIpv4AllRouteSourceForwardingEnable, f3L3TrafficIpv4AllRouteAdminDistance,
        f3L3TrafficIpv4AllRouteStatus, f3L3TrafficIpv4AllRouteStorageType, f3L3TrafficIpv4AllRouteRowStatus,
        
        f3L3TrafficIpv6StaticRouteDest, f3L3TrafficIpv6StaticRoutePrefixLength, f3L3TrafficIpv6StaticRouteNextHop,
        f3L3TrafficIpv6StaticRouteInterface, f3L3TrafficIpv6StaticRouteMetric, f3L3TrafficIpv6StaticRouteStorageType, 
        f3L3TrafficIpv6StaticRouteRowStatus,
        
        f3L3TrafficIpv6AllRouteDest, f3L3TrafficIpv6AllRoutePrefixLength, f3L3TrafficIpv6AllRouteNextHop,
        f3L3TrafficIpv6AllRouteInterface, f3L3TrafficIpv6AllRouteOrigin, f3L3TrafficIpv6AllRouteMetric,
        f3L3TrafficIpv6AllRouteAdminDistance, f3L3TrafficIpv6AllRouteStatus, f3L3TrafficIpv6AllRouteStorageType,
        f3L3TrafficIpv6AllRouteRowStatus,
        
        f3IpPrefixListIndex, f3IpPrefixListName, f3IpPrefixListDefaultDisposition,
        f3IpPrefixListStorageType, f3IpPrefixListRowStatus,
        
        f3IpPrefixIndex, f3IpPrefix, f3IpPrefixPriority, f3IpPrefixDisposition,
        f3IpPrefixLessOrEqualPrefixLen, f3IpPrefixGreaterOrEqualPrefixLen, f3IpPrefixStorageType,
        f3IpPrefixRowStatus
    }
    STATUS  current
    DESCRIPTION
            "A collection of objects used to manage the L3 functionality."
    ::= { f3L3Groups 1 }

f3L3PerfGroup OBJECT-GROUP
    OBJECTS {
        f3L3FlowPointStatsIndex,f3L3FlowPointStatsIntervalType,f3L3FlowPointStatsValid,
        f3L3FlowPointStatsAction,f3L3FlowPointStatsFMG,f3L3FlowPointStatsFMY,f3L3FlowPointStatsFMRD,
        f3L3FlowPointStatsFTD,f3L3FlowPointStatsFragmentedDropAcl,f3L3FlowPointStatsAclRuleDrop,
        f3L3FlowPointStatsTtlEqual1Drop,f3L3FlowPointStatsFrameTx,f3L3FlowPointStatsFrameRx,
        f3L3FlowPointStatsNoRouteDrop, f3L3FlowPointStatsHopLimitDrop,

        f3L3FlowPointHistoryIndex,f3L3FlowPointHistoryTime,f3L3FlowPointHistoryValid,
        f3L3FlowPointHistoryAction,f3L3FlowPointHistoryFMG,f3L3FlowPointHistoryFMY,
        f3L3FlowPointHistoryFMRD,f3L3FlowPointHistoryFTD,f3L3FlowPointHistoryFragmentedDropAcl,
        f3L3FlowPointHistoryAclRuleDrop,f3L3FlowPointHistoryTtlEqual1Drop,f3L3FlowPointHistoryFrameTx,
        f3L3FlowPointHistoryFrameRx,f3L3FlowPointHistoryNoRouteDrop, f3L3FlowPointHistoryHopLimitDrop,

        f3L3FlowPointThresholdIndex,f3L3FlowPointThresholdInterval,f3L3FlowPointThresholdVariable,
        f3L3FlowPointThresholdValueLo,f3L3FlowPointThresholdValueHi,f3L3FlowPointThresholdMonValue,

        f3L3TrafficIpInterfaceStatsIndex,f3L3TrafficIpInterfaceStatsIntervalType,
        f3L3TrafficIpInterfaceStatsValid,f3L3TrafficIpInterfaceStatsAction,f3L3TrafficIpInterfaceStatsDhcpTx,
        f3L3TrafficIpInterfaceStatsDhcpRx,f3L3TrafficIpInterfaceStatsIcmpTx,
        f3L3TrafficIpInterfaceStatsIcmpRx,f3L3TrafficIpInterfaceStatsArpReqTx,f3L3TrafficIpInterfaceStatsArpReqRx,
        f3L3TrafficIpInterfaceStatsArpReplyTx,f3L3TrafficIpInterfaceStatsArpReplyRx,
        f3L3TrafficIpInterfaceStatsDhcpV6Tx,f3L3TrafficIpInterfaceStatsDhcpV6Rx,
        f3L3TrafficIpInterfaceStatsIcmpV6WONdpTx,f3L3TrafficIpInterfaceStatsIcmpV6WONdpRx,
        f3L3TrafficIpInterfaceStatsNdpNSTx,f3L3TrafficIpInterfaceStatsNdpNSRx,
        f3L3TrafficIpInterfaceStatsNdpNATx,f3L3TrafficIpInterfaceStatsNdpNARx,
        f3L3TrafficIpInterfaceStatsNdpRATx,f3L3TrafficIpInterfaceStatsNdpRARx,
        f3L3TrafficIpInterfaceStatsNdpRSTx,f3L3TrafficIpInterfaceStatsNdpRSRx,

        f3L3TrafficIpInterfaceHistoryIndex,f3L3TrafficIpInterfaceHistoryTime,f3L3TrafficIpInterfaceHistoryValid,
        f3L3TrafficIpInterfaceHistoryAction,f3L3TrafficIpInterfaceHistoryDhcpTx,f3L3TrafficIpInterfaceHistoryDhcpRx,
        f3L3TrafficIpInterfaceHistoryIcmpTx,f3L3TrafficIpInterfaceHistoryIcmpRx,
        f3L3TrafficIpInterfaceHistoryArpReqTx,f3L3TrafficIpInterfaceHistoryArpReqRx,f3L3TrafficIpInterfaceHistoryArpReplyTx,
        f3L3TrafficIpInterfaceHistoryArpReplyRx,f3L3TrafficIpInterfaceHistoryDhcpV6Tx,
        f3L3TrafficIpInterfaceHistoryDhcpV6Rx,f3L3TrafficIpInterfaceHistoryIcmpV6WONdpTx,
        f3L3TrafficIpInterfaceHistoryIcmpV6WONdpRx,f3L3TrafficIpInterfaceHistoryNdpNSTx,
        f3L3TrafficIpInterfaceHistoryNdpNSRx,f3L3TrafficIpInterfaceHistoryNdpNATx,
        f3L3TrafficIpInterfaceHistoryNdpNARx,f3L3TrafficIpInterfaceHistoryNdpRATx,
        f3L3TrafficIpInterfaceHistoryNdpRARx,f3L3TrafficIpInterfaceHistoryNdpRSTx,
        f3L3TrafficIpInterfaceHistoryNdpRSRx,

        f3L3TrafficIpInterfaceThresholdIndex,f3L3TrafficIpInterfaceThresholdInterval,f3L3TrafficIpInterfaceThresholdVariable,
        f3L3TrafficIpInterfaceThresholdValueLo,f3L3TrafficIpInterfaceThresholdValueHi,f3L3TrafficIpInterfaceThresholdMonValue,

        f3L3AclRuleStatsIndex,f3L3AclRuleStatsIntervalType,f3L3AclRuleStatsValid,f3L3AclRuleStatsAction,
        f3L3AclRuleStatsRuleMatch,

        f3L3AclRuleHistoryIndex,f3L3AclRuleHistoryTime,f3L3AclRuleHistoryValid,f3L3AclRuleHistoryAction,
        f3L3AclRuleHistoryRuleMatch,

        f3L3AclRuleThresholdIndex,f3L3AclRuleThresholdInterval,f3L3AclRuleThresholdVariable,
        f3L3AclRuleThresholdValueLo,f3L3AclRuleThresholdValueHi,f3L3AclRuleThresholdMonValue,
        
        f3L2A2NAclRuleStatsIndex,f3L2A2NAclRuleStatsIntervalType,f3L2A2NAclRuleStatsValid,f3L2A2NAclRuleStatsAction,
        f3L2A2NAclRuleStatsRuleMatch,

        f3L2A2NAclRuleHistoryIndex,f3L2A2NAclRuleHistoryTime,f3L2A2NAclRuleHistoryValid,f3L2A2NAclRuleHistoryAction,
        f3L2A2NAclRuleHistoryRuleMatch,

        f3L2A2NAclRuleThresholdIndex,f3L2A2NAclRuleThresholdInterval,f3L2A2NAclRuleThresholdVariable,
        f3L2A2NAclRuleThresholdValueLo,f3L2A2NAclRuleThresholdValueHi,f3L2A2NAclRuleThresholdMonValue,

        f3L2N2AAclRuleStatsIndex,f3L2N2AAclRuleStatsIntervalType,f3L2N2AAclRuleStatsValid,f3L2N2AAclRuleStatsAction,
        f3L2N2AAclRuleStatsRuleMatch,

        f3L2N2AAclRuleHistoryIndex,f3L2N2AAclRuleHistoryTime,f3L2N2AAclRuleHistoryValid,f3L2N2AAclRuleHistoryAction,
        f3L2N2AAclRuleHistoryRuleMatch,

        f3L2N2AAclRuleThresholdIndex,f3L2N2AAclRuleThresholdInterval,f3L2N2AAclRuleThresholdVariable,
        f3L2N2AAclRuleThresholdValueLo,f3L2N2AAclRuleThresholdValueHi,f3L2N2AAclRuleThresholdMonValue,

        f3L3QosPolicerStatsIndex,f3L3QosPolicerStatsIntervalType,f3L3QosPolicerStatsValid,
        f3L3QosPolicerStatsAction,f3L3QosPolicerStatsFMG,f3L3QosPolicerStatsFMY,
        f3L3QosPolicerStatsFMYD,f3L3QosPolicerStatsFMRD,f3L3QosPolicerStatsBytesIn,
        f3L3QosPolicerStatsBytesOut,f3L3QosPolicerStatsABR,

        f3L3QosPolicerHistoryIndex,f3L3QosPolicerHistoryTime,f3L3QosPolicerHistoryValid,
        f3L3QosPolicerHistoryAction,f3L3QosPolicerHistoryFMG,f3L3QosPolicerHistoryFMY,
        f3L3QosPolicerHistoryFMYD,f3L3QosPolicerHistoryFMRD,f3L3QosPolicerHistoryBytesIn,
        f3L3QosPolicerHistoryBytesOut,f3L3QosPolicerHistoryABR,

        f3L3QosPolicerThresholdIndex,
        f3L3QosPolicerThresholdInterval,f3L3QosPolicerThresholdVariable,f3L3QosPolicerThresholdValueLo,
        f3L3QosPolicerThresholdValueHi,f3L3QosPolicerThresholdMonValue,

        f3L3QosShaperStatsIndex,f3L3QosShaperStatsIntervalType,f3L3QosShaperStatsValid,
        f3L3QosShaperStatsAction,f3L3QosShaperStatsBT,f3L3QosShaperStatsBTD,f3L3QosShaperStatsFD,
        f3L3QosShaperStatsFTD,f3L3QosShaperStatsBR,f3L3QosShaperStatsFR,
        f3L3QosShaperStatsABRRL,f3L3QosShaperStatsBREDD,f3L3QosShaperStatsFREDD,

        f3L3QosShaperHistoryIndex,f3L3QosShaperHistoryTime,f3L3QosShaperHistoryValid,
        f3L3QosShaperHistoryAction,f3L3QosShaperHistoryBT,f3L3QosShaperHistoryBTD,
        f3L3QosShaperHistoryFD,f3L3QosShaperHistoryFTD,f3L3QosShaperHistoryBR,
        f3L3QosShaperHistoryFR,f3L3QosShaperHistoryABRRL,f3L3QosShaperHistoryBREDD,
        f3L3QosShaperHistoryFREDD,

        f3L3QosShaperThresholdIndex,f3L3QosShaperThresholdInterval,f3L3QosShaperThresholdVariable,
        f3L3QosShaperThresholdValueLo,f3L3QosShaperThresholdValueHi,f3L3QosShaperThresholdMonValue,
        cmL3FlowPointStatsIndex, cmL3FlowPointStatsIntervalType, cmL3FlowPointStatsValid, 
        cmL3FlowPointStatsAction, cmL3FlowPointStatsFMG, cmL3FlowPointStatsFMY, cmL3FlowPointStatsFMRD, 
        cmL3FlowPointStatsFTD, cmL3FlowPointStatsFragmentedDropAcl, cmL3FlowPointStatsAclRuleDrop, 
        cmL3FlowPointStatsTtlEqual1Drop, cmL3FlowPointStatsFrameTx, cmL3FlowPointStatsFrameRx, cmL3FlowPointStatsNoRouteDrop, 
        cmL3FlowPointStatsAclDropNoMatch, cmL3FlowPointHistoryIndex, cmL3FlowPointHistoryTime, cmL3FlowPointHistoryValid, 
        cmL3FlowPointHistoryAction, cmL3FlowPointHistoryFMG, cmL3FlowPointHistoryFMY, cmL3FlowPointHistoryFMRD, 
        cmL3FlowPointHistoryFTD, cmL3FlowPointHistoryFragmentedDropAcl, cmL3FlowPointHistoryAclRuleDrop, 
        cmL3FlowPointHistoryTtlEqual1Drop, cmL3FlowPointHistoryFrameTx, cmL3FlowPointHistoryFrameRx, cmL3FlowPointHistoryNoRouteDrop, 
        cmL3FlowPointHistoryAclDropNoMatch,

        cmL3FlowPointThresholdIndex, cmL3FlowPointThresholdInterval, cmL3FlowPointThresholdVariable, 
        cmL3FlowPointThresholdValueLo, cmL3FlowPointThresholdValueHi, cmL3FlowPointThresholdMonValue, 
        cmL3QosPolicerStatsIndex, cmL3QosPolicerStatsIntervalType, cmL3QosPolicerStatsValid, 
        cmL3QosPolicerStatsAction, cmL3QosPolicerStatsFMG, cmL3QosPolicerStatsFMY, cmL3QosPolicerStatsFMYD, 
        cmL3QosPolicerStatsFMRD, cmL3QosPolicerStatsBytesIn, cmL3QosPolicerStatsBytesOut, cmL3QosPolicerStatsABR,

        cmL3QosPolicerHistoryIndex, cmL3QosPolicerHistoryTime, cmL3QosPolicerHistoryValid, cmL3QosPolicerHistoryAction, 
        cmL3QosPolicerHistoryFMG, cmL3QosPolicerHistoryFMY, cmL3QosPolicerHistoryFMYD, cmL3QosPolicerHistoryFMRD, 
        cmL3QosPolicerHistoryBytesIn, cmL3QosPolicerHistoryBytesOut, cmL3QosPolicerHistoryABR,
        cmL3QosPolicerThresholdIndex, cmL3QosPolicerThresholdInterval, cmL3QosPolicerThresholdVariable, 
        cmL3QosPolicerThresholdValueLo, cmL3QosPolicerThresholdValueHi, cmL3QosPolicerThresholdMonValue,
        cmL3QosShaperStatsIndex, cmL3QosShaperStatsIntervalType, cmL3QosShaperStatsValid, cmL3QosShaperStatsAction, 
        cmL3QosShaperStatsBT, cmL3QosShaperStatsBTD, cmL3QosShaperStatsFD, cmL3QosShaperStatsFTD, cmL3QosShaperStatsBR, 
        cmL3QosShaperStatsFR, cmL3QosShaperStatsABRRL, cmL3QosShaperStatsABRRLR, cmL3QosShaperStatsBREDD, cmL3QosShaperStatsFREDD,
        cmL3QosShaperHistoryFTD, cmL3QosShaperHistoryBR, cmL3QosShaperHistoryFR, cmL3QosShaperHistoryABRRL, 
        cmL3QosShaperHistoryABRRLR, cmL3QosShaperHistoryBREDD, cmL3QosShaperHistoryFREDD, 

        cmL3QosShaperThresholdIndex, cmL3QosShaperThresholdInterval, cmL3QosShaperThresholdVariable, 
        cmL3QosShaperThresholdValueLo, cmL3QosShaperThresholdValueHi, cmL3QosShaperThresholdMonValue

    }
    STATUS  current
    DESCRIPTION
            "A collection of objects performance used to manage the L3 functionality."
    ::= { f3L3Groups 2 }

f3L3TrafficOspfGroup OBJECT-GROUP
    OBJECTS {
        f3VrfOspfRouterIndex,
        f3VrfOspfRouterAdminState,
        f3VrfOspfRouterSecondaryState,
        f3VrfOspfRouterOperationalState,
        f3VrfOspfRouterId,
        f3VrfOspfRouterDescription,
        f3VrfOspfRouterBgpRoutesRedistributeToOspf,
        f3VrfOspfRouterBgpRoutesMetricType,
        f3VrfOspfRouterBgpRoutesMetric,
        f3VrfOspfRouterStaticRoutesRedistributeToOspf,
        f3VrfOspfRouterStaticRoutesMetricType,
        f3VrfOspfRouterStaticRoutesMetric,
        f3VrfOspfRouterConnectedRoutesRedistributeToOspf,
        f3VrfOspfRouterConnectedRoutesMetricType,
        f3VrfOspfRouterConnectedRoutesMetric,
        f3VrfOspfRouterDhcpRoutesRedistributeToOspf,
        f3VrfOspfRouterDhcpRoutesMetricType,
        f3VrfOspfRouterDhcpRoutesMetric,
        f3VrfOspfRouterStorageType,
        f3VrfOspfRouterRowStatus,
        f3VrfOspfRouterAction,
        f3VrfOspfRouterVersion,
        f3VrfOspfRouterAdministrativeDistance,
        f3VrfOspfRouterSlaacRoutesRedistributeToOspf,
        f3VrfOspfRouterSlaacRoutesMetricType,
        f3VrfOspfRouterSlaacRoutesMetric,
        f3VrfOspfRouterEcmpMaximumPaths,
        f3VrfOspfRouterSrControl,
        f3VrfOspfRouterConvergenceTime,
        
        f3L3TrafficOspfAreaIndex,
        f3L3TrafficOspfAreaType,
        f3L3TrafficOspfAreaDefaultCost,
        f3L3TrafficOspfAreaId,
        f3L3TrafficOspfAreaStorageType,
        f3L3TrafficOspfAreaRowStatus,
        f3L3TrafficOspfAreaAuthType,
        f3L3TrafficOspfAreaSimpleAuthKey,
        f3L3TrafficOspfAreaCryptoKeyId,
        
        f3L3TrafficOspfAreaIfMemberObject,
        f3L3TrafficOspfAreaIfMemberStorageType,
        f3L3TrafficOspfAreaIfMemberRowStatus,
        
        f3VrfLoopbackInterfaceIndex,
        f3VrfLoopbackInterfaceName,
        f3VrfLoopbackInterfaceIpAddress,
        f3VrfLoopbackInterfaceNetMask,
        f3VrfLoopbackInterfaceCIRLo,
        f3VrfLoopbackInterfaceCIRHi,
        f3VrfLoopbackInterfaceStorageType,
        f3VrfLoopbackInterfaceRowStatus,
        f3VrfLoopbackInterfaceIpMode,
        f3VrfLoopbackInterfaceIpv6Address,
        f3VrfLoopbackInterfaceIpv6AddrPrefixLen,
        
        f3L3TrafficOspfAsLsDbType,
        f3L3TrafficOspfAsLsDbId,
        f3L3TrafficOspfAsLsDbRouterId,
        f3L3TrafficOspfAsLsDbChecksum,
        f3L3TrafficOspfAsLsDbSeqNum,
        f3L3TrafficOspfAsLsDbAge,
        
        f3L3TrafficOspfLsDbType,
        f3L3TrafficOspfLsDbId,
        f3L3TrafficOspfLsDbRouterId,
        f3L3TrafficOspfLsDbAreaId,
        f3L3TrafficOspfLsDbChecksum,
        f3L3TrafficOspfLsDbSeqNum,
        f3L3TrafficOspfLsDbAge,
        
        f3L3TrafficOspfNeighborIpAddress,
        f3L3TrafficOspfNeighborInterface,
        f3L3TrafficOspfNeighborRouterId,
        f3L3TrafficOspfNeighborState,
        f3L3TrafficOspfNeighborRole,
        f3L3TrafficOspfNeighborPriority,
        f3L3TrafficOspfNeighborDeadTime,
        f3L3TrafficOspfNeighborLocalInterfaceName,
        
        f3L3TrafficIPIfOspfAreaId,
        f3L3TrafficIPIfOspfCost,
        f3L3TrafficIPIfOspfIfType,
        f3L3TrafficIPIfOspfRtrPriority,
        f3L3TrafficIPIfOspfHelloInterval,
        f3L3TrafficIPIfOspfDeadInterval,
        f3L3TrafficIPIfOspfTransmitDelay,
        f3L3TrafficIPIfOspfRetransmitInterval,
        f3L3TrafficIPIfOspfState,
        f3L3TrafficIPIfOspfDesignatedRouterId,
        f3L3TrafficIPIfOspfBackupDesignatedRouterId,
        f3L3TrafficIPIfOspfAuthType,
        f3L3TrafficIPIfOspfSimpleAuthKey,
        f3L3TrafficIPIfospfCryptoKeyId,

        f3L3TrafficOspfInterfaceIndex,
        f3L3TrafficOspfInterfaceOspfCost,
        f3L3TrafficOspfInterfaceType,
        f3L3TrafficOspfInterfaceOspfRtrPriority,
        f3L3TrafficOspfInterfaceOspfHelloInterval,
        f3L3TrafficOspfInterfaceOspfDeadInterval,
        f3L3TrafficOspfInterfaceOspfTransmitDelay,
        f3L3TrafficOspfInterfaceOspfRetransmitInterval,
        f3L3TrafficOspfInterfaceState,
        f3L3TrafficOspfInterfaceOspfDesignatedRouterId,
        f3L3TrafficOspfInterfaceOspfBackupDesignatedRouterId,
        f3L3TrafficOspfInterfaceOspfAuthType,
        f3L3TrafficOspfInterfaceOspfSimpleAuthKey,
        f3L3TrafficOspfInterfaceOspfCryptoKeyId,
        f3L3TrafficOspfInterfaceOspfInstanceId,
        f3L3TrafficOspfInterfaceId,
        f3L3TrafficOspfInterfaceLinkLsaSuppression,
        f3L3TrafficOspfInterfacePassiveControl,
        f3L3TrafficOspfInterfaceAssociatedIpInterface,
        f3L3TrafficOspfInterfaceStorageType,
        f3L3TrafficOspfInterfaceRowStatus,
        f3L3TrafficOspfInterfaceTilfaControl,
        f3L3TrafficOspfInterfaceTilfaProtectionType,

        f3L3TrafficOspfV3NeighborRouterId,
        f3L3TrafficOspfV3NeighborInterfaceId,
        f3L3TrafficOspfV3NeighborPriority,
        f3L3TrafficOspfV3NeighborDeadTime,
        f3L3TrafficOspfV3NeighborLocalInterfaceName,
        f3L3TrafficOspfV3NeighborState,
        f3L3TrafficOspfV3NeighborRole,
        f3L3TrafficOspfV3NeighborIpAddress,
        
        f3L3TrafficOspfLinkLsDbInterfaceId,
        f3L3TrafficOspfLinkLsDbInterface,
        f3L3TrafficOspfLinkLsDbType,
        f3L3TrafficOspfLinkLsDbId,
        f3L3TrafficOspfLinkLsDbAdvRouterId,
        f3L3TrafficOspfLinkLsDbAreaId,
        f3L3TrafficOspfLinkLsDbChecksum,
        f3L3TrafficOspfLinkLsDbSeqNum,
        f3L3TrafficOspfLinkLsDbAge,
        f3L3TrafficOspfLinkLsDbRtrPriority,
        f3L3TrafficOspfLinkLsDbLinkLocalAddress,
        f3L3TrafficOspfLinkLsDbPrefixList,

        f3L3TrafficOspfAreaRouteSummaryPrefix,
        f3L3TrafficOspfAreaRouteSummaryCost,
        f3L3TrafficOspfAreaRouteSummaryAdvertise,
        f3L3TrafficOspfAreaRouteSummaryStorageType,
        f3L3TrafficOspfAreaRouteSummaryRowStatus
    }
    STATUS  current
    DESCRIPTION
            "A collection of objects used to manage the L3 Ospf functionality."
    ::= { f3L3Groups 3 }

f3L3TrafficIPv6Group OBJECT-GROUP
    OBJECTS {
        f3L3TrafficIPv6IfIndex,
        f3L3TrafficIPv6IfName,
        f3L3TrafficIPv6IfAdminState,
        f3L3TrafficIPv6IfSecondaryState,
        f3L3TrafficIPv6IfOperationalState,
        f3L3TrafficIPv6IfType,
        f3L3TrafficIPv6IfLinkLocalAddr,
        f3L3TrafficIPv6IfLinkLocalAddrMode,
        f3L3TrafficIPv6IfMtu,
        f3L3TrafficIPv6IfStatelessAddrAutoconfigEnabled,
        f3L3TrafficIPv6IfDefaultGateway,
        f3L3TrafficIPv6IfIcmpErrorMsgRateLimit,
        f3L3TrafficIPv6IfDhcpRole,
        f3L3TrafficIPv6IfDhcpEnabled,
        f3L3TrafficIPv6IfDhcpRapidCommitControlEnabled,
        f3L3TrafficIPv6IfMaxRAInterval,
        f3L3TrafficIPv6IfMinRAInterval,
        f3L3TrafficIPv6IfRouterLifeTime,
        f3L3TrafficIPv6IfReachableTime,
        f3L3TrafficIPv6IfRaDhcpMoreConfigEnabled,
        f3L3TrafficIPv6IfRaManagedAddressConfigEnabled,
        f3L3TrafficIPv6IfRaRDNSSOptionEnabled,
        f3L3TrafficIPv6IfRaRDNSSLifeTime,
        f3L3TrafficIPv6IfRaDNSSList,
        f3L3TrafficIPv6IfRaDefaultRouterPreference,
        f3L3TrafficIPv6IfDupAddrDetectControl,
        f3L3TrafficIPv6IfDupAddrDetectTransmits,
        f3L3TrafficIPv6IfDupAddrDetectRetransTimer,
        f3L3TrafficIPv6IfStorageType,
        f3L3TrafficIPv6IfRowStatus,
        f3L3TrafficIPv6IfAction,
        
        f3L3TrafficIPv6AddrIndex,
        f3L3TrafficIPv6AddrAssignMode,
        f3L3TrafficIPv6AddrUnicastAddr,
        f3L3TrafficIPv6AddrUnicastAddrPrefixLength,
        f3L3TrafficIPv6AddrUnicastAddrAutoGenPrefix,
        f3L3TrafficIPv6AddrStorageType,
        f3L3TrafficIPv6AddrRowStatus,
        
        f3L3TrafficIPv6PrefixIndex,
        f3L3TrafficIPv6PrefixRaPrefixAdvEnabled,
        f3L3TrafficIPv6PrefixRaPrefix,
        f3L3TrafficIPv6PrefixRaPrefixLength,
        f3L3TrafficIPv6PrefixValidLifeTime,
        f3L3TrafficIPv6PrefixPreferredLifeTime,
        f3L3TrafficIPv6PrefixStorageType,
        f3L3TrafficIPv6PrefixRowStatus,
        
        f3L3TrafficIPv6NdpIPv6Addr,
        f3L3TrafficIPv6NdpInterface,
        f3L3TrafficIPv6NdpMacAddress,
        f3L3TrafficIPv6NdpType,
        f3L3TrafficIPv6NdpReachabilityState,
        f3L3TrafficIPv6NdpAge,
        f3L3TrafficIPv6NdpStorageType,
        f3L3TrafficIPv6NdpRowStatus,
        
        f3L3TrafficIpv6RouteDest,
        f3L3TrafficIpv6RoutePrefixLength,
        f3L3TrafficIpv6RouteGateway,
        f3L3TrafficIpv6RouteInterface,
        f3L3TrafficIpv6RouteMetric,
        f3L3TrafficIpv6RouteType,
        f3L3TrafficIpv6RouteAdvertise,
        f3L3TrafficIpv6RouteStatus,
        f3L3TrafficIpv6RouteFlags,
        f3L3TrafficIpv6RouteOrigin,
        f3L3TrafficIpv6RouteStorageType,
        f3L3TrafficIpv6RouteRowStatus,
        
        f3DhcpV6RelayAgentIndex,
        f3DhcpV6RelayAgentAlias,
        f3DhcpV6RelayAgentAdminState,
        f3DhcpV6RelayAgentSecondaryState,
        f3DhcpV6RelayAgentOperationalState,
        f3DhcpV6RelayAgentServerIpAddress,
        f3DhcpV6RelayAgentServerIpInteface,
        f3DhcpV6RelayAgentStorageType,
        f3DhcpV6RelayAgentRowStatus,
        
        f3DhcpV6RelayAgentServerIpAddressList,

        f3DhcpV6RelayAgentClientTrafficIpIfMemberObject,
        f3DhcpV6RelayAgentClientTrafficIpIfMemberStorageType,
        f3DhcpV6RelayAgentClientTrafficIpIfMemberRowStatus,
        
        f3L3TrafficIPInterfaceIPv6AddressIndex,
        f3L3TrafficIPInterfaceIPv6AddressAssignMode,
        f3L3TrafficIPInterfaceIPv6AddressUnicastAddr,
        f3L3TrafficIPInterfaceIPv6AddressUnicastAddrPrefixLength,
        f3L3TrafficIPInterfaceIPv6AddressUnicastAddrAutoGenPrefix,
        f3L3TrafficIPInterfaceIPv6AddressStorageType,
        f3L3TrafficIPInterfaceIPv6AddressRowStatus,
        
        f3L3TrafficIPInterfaceRAPrefixIndex,
        f3L3TrafficIPInterfaceRAPrefixAdvertiseEnabled,
        f3L3TrafficIPInterfaceRAPrefix,
        f3L3TrafficIPInterfaceRAPrefixLength,
        f3L3TrafficIPInterfaceRAPrefixValidLifeTime,
        f3L3TrafficIPInterfaceRAPrefixPreferredLifeTime,
        f3L3TrafficIPInterfaceRAPrefixStorageType,
        f3L3TrafficIPInterfaceRAPrefixRowStatus,
        
        f3L3TrafficIPInterfaceNdpIPv6Addr,
        f3L3TrafficIPInterfaceNdpInterface,
        f3L3TrafficIPInterfaceNdpMacAddress,
        f3L3TrafficIPInterfaceNdpType,
        f3L3TrafficIPInterfaceNdpReachabilityState,
        f3L3TrafficIPInterfaceNdpAge,
        f3L3TrafficIPInterfaceNdpStorageType,
        f3L3TrafficIPInterfaceNdpRowStatus
    }
    STATUS  current
    DESCRIPTION
            "A collection of objects used to manage the traffic ipv6 functionality."
    ::= { f3L3Groups 4 }

f3L3TrafficBgpGroup OBJECT-GROUP
    OBJECTS {
        f3L3TrafficBgpRouterIndex, 
        f3L3TrafficBgpRouterAdminState, 
        f3L3TrafficBgpRouterSecondaryState, 
        f3L3TrafficBgpRouterOperationalState,
        f3L3TrafficBgpRouterId, 
        f3L3TrafficBgpRouterAsNumber,
        f3L3TrafficBgpRouterConnectedRoutesRedistControl, 
        f3L3TrafficBgpRouterOspfRoutesRedistControl,
        f3L3TrafficBgpRouterStaticRoutesRedistControl,
        f3L3TrafficBgpRouterDhcpRoutesRedistControl,
        f3L3TrafficBgpRouterStorageType,
        f3L3TrafficBgpRouterRowStatus,
        f3L3TrafficBgpRouterAction,
        f3L3TrafficBgpRouterIBgpAdminDistance,
        f3L3TrafficBgpRouterEBgpAdminDistance,
        f3L3TrafficBgpRouterEcmpMaximumPaths,
        f3L3TrafficBgpRouterRestartTime,
        f3L3TrafficBgpRouterStaleRoutesTime,
        
        f3L3TrafficBgpRouteNetwork,
        f3L3TrafficBgpRouteMetric,
        f3L3TrafficBgpRouteNextHop,
        f3L3TrafficBgpRoutePath,
        
        f3L3TrafficBgpPeerIndex,
        f3L3TrafficBgpPeerAdminState,
        f3L3TrafficBgpPeerSecondaryState,
        f3L3TrafficBgpPeerOperationalState,
        f3L3TrafficBgpPeerIpv4Addr,
        f3L3TrafficBgpPeerAsNumber,
        f3L3TrafficBgpPeerDescription,
        f3L3TrafficBgpPeerBgpSessionState,
        f3L3TrafficBgpPeerHoldTime,
        f3L3TrafficBgpPeerStartupHoldTime,
        f3L3TrafficBgpPeerKeepAliveTime,
        f3L3TrafficBgpPeerConnectRetryTime,
        f3L3TrafficBgpPeerUpdateSourceIp,
        f3L3TrafficBgpPeerAuthenticationKey,
        f3L3TrafficBgpPeerTimeSinceUpTransition,
        f3L3TrafficBgpPeerTimeSinceDownTransition,
        f3L3TrafficBgpPeerStorageType,
        f3L3TrafficBgpPeerRowStatus,
        f3L3TrafficBgpPeerIpVersion,
        f3L3TrafficBgpPeerIpv6Address,
        f3L3TrafficBgpPeerUpdateSourceIpv6,
        f3L3TrafficBgpPeerMultihopControl,
        f3L3TrafficBgpPeerMultihopTtl,
        f3L3TrafficBgpPeerUpdateSourceInterface,
        f3L3TrafficBgpPeerUpdateSourceType,
        f3L3TrafficBgpPeerLocalPreference,
        f3L3TrafficBgpPeerRouteReflectorClient,
        f3L3TrafficBgpPeerRouteReflectorClusterId,
        f3L3TrafficBgpPeerBgpRouteInboundFilter,
        f3L3TrafficBgpPeerBgpRouteOutboundFilter,
        f3L3TrafficBgpPeerBgpGracefulRestart,
        f3L3TrafficBgpPeerPeerRestartTime,
        f3L3TrafficBgpPeerPeerRestarting,
        
        f3L3TrafficBgpPeerAddressFamilyIndex,
        f3L3TrafficBgpPeerAddressFamilyName,
        f3L3TrafficBgpPeerAddressFamilyRedistOspfRoute,
        f3L3TrafficBgpPeerAddressFamilyRedistConnectedRoute,
        f3L3TrafficBgpPeerAddressFamilyRedistStaticRoute,
        f3L3TrafficBgpPeerAddressFamilyRedistDhcpRoute,
        f3L3TrafficBgpPeerAddressFamilyRedistSlaacRoute,
        f3L3TrafficBgpPeerAddressFamilySendDefaultRoute,
        f3L3TrafficBgpPeerAddressFamilyNextHopType,
        f3L3TrafficBgpPeerAddressFamilyNextHopIpv4,
        f3L3TrafficBgpPeerAddressFamilyNextHopIpv6,
        f3L3TrafficBgpPeerAddressFamilyExtNextHopControl,
        f3L3TrafficBgpPeerAddressFamilyStorageType,
        f3L3TrafficBgpPeerAddressFamilyRowStatus,
        
        f3L3TrafficBgpRIBRouteIndex,
        f3L3TrafficBgpRIBRouteNetwork,
        f3L3TrafficBgpRIBRouteNextHop,
        f3L3TrafficBgpRIBRouteMetric,
        f3L3TrafficBgpRIBRoutePath,
        
        f3L3TrafficBgpRouteV2Network,
        f3L3TrafficBgpRouteV2NextHop,
        f3L3TrafficBgpRouteV2Metric,
        f3L3TrafficBgpRouteV2Path,
        f3L3TrafficBgpRouteV2LocalPreference,
        
        f3L3TrafficBgpPeerAddressFamilyAdvPrefix,
        f3L3TrafficBgpPeerAddressFamilyAdvPrefixStorageType,
        f3L3TrafficBgpPeerAddressFamilyAdvPrefixRowStatus,
        
        f3L3TrafficBgpInRouteIndex,
        f3L3TrafficBgpInRouteNetwork,
        f3L3TrafficBgpInRouteNextHop,
        f3L3TrafficBgpInRouteMetric,
        f3L3TrafficBgpInRoutePath,
        f3L3TrafficBgpInRouteLocalPreference
    }
    STATUS  current
    DESCRIPTION
            "A collection of objects used to manage the traffic BGP functionality."
    ::= { f3L3Groups 5 }

f3L3DhcpGroup OBJECT-GROUP
    OBJECTS {
        f3L3DhcpClassIndex, f3L3DhcpClassStorageType,
        f3L3DhcpClassRowStatus, f3L3DhcpRuleIndex, f3L3DhcpRuleType,
        f3L3DhcpRuleValue, f3L3DhcpRuleStorageType,
        f3L3DhcpRuleRowStatus, f3L3DhcpIPv4AddrPoolIndex,
        f3L3DhcpIPv4AddrPoolStartAddr, f3L3DhcpIPv4AddrPoolEndAddr,
        f3L3DhcpIPv4AddrPoolClass, f3L3DhcpIPv4AddrPoolLeaseTime,
        f3L3DhcpIPv4AddrPoolGatewayList, f3L3DhcpIPv4AddrPoolDnsList,
        f3L3DhcpIPv4AddrPoolTotalCount,
        f3L3DhcpIPv4AddrPoolAllocatedCount, f3L3DhcpIPv4AddrPoolAction,
        f3L3DhcpIPv4AddrPoolActionIPv4Addr,
        f3L3DhcpIPv4AddrPoolStorageType, f3L3DhcpIPv4AddrPoolRowStatus,
        f3L3DhcpExcludedIPv4AddrListStartAddr,
        f3L3DhcpExcludedIPv4AddrListEndAddr,
        f3L3DhcpExcludedIPv4AddrListStorageType,
        f3L3DhcpExcludedIPv4AddrListRowStatus,
        f3L3DhcpStaticBindingIPv4AddrIpAddr,
        f3L3DhcpStaticBindingIPv4AddrBindType,
        f3L3DhcpStaticBindingIPv4AddrLeaseTime,
        f3L3DhcpStaticBindingIPv4AddrValue,
        f3L3DhcpStaticBindingIPv4AddrStorageType,
        f3L3DhcpStaticBindingIPv4AddrRowStatus,
        f3L3DhcpActiveLeaseIPv4AddrIpAddr,
        f3L3DhcpActiveLeaseIPv4AddrVendorClassId,
        f3L3DhcpActiveLeaseIPv4AddrLeaseTime,
        f3L3DhcpActiveLeaseIPv4AddrExpireTime,
        f3L3DhcpActiveLeaseIPv4AddrMacAddr,
        f3L3DhcpActiveLeaseIPv4AddrClientId
    }
    STATUS  current
    DESCRIPTION
            "A collection of objects used to manage the l3 dhcp functionality."
    ::= { f3L3Groups 6 }

END
