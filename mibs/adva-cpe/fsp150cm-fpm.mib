F3-FPM-MIB DEFINITIONS ::= BEGIN

IMPORTS
    MODULE-COMPLIANCE, OBJECT-GROUP 
             FROM SNMPv2-CONF
    MODULE-IDENTITY, OBJECT-TYPE, Integer32, Unsigned32, Counter64
             FROM SNMPv2-SMI
    TruthValue, RowStatus, StorageType, 
    VariablePointer, TEXTUAL-CONVENTION, DisplayString, DateAndTime
             FROM SNMPv2-TC
    VlanId, AdminState, OperationalState, SecondaryState,
    VlanPriority, CmPmIntervalType, PerfCounter64, CmPmBinAction
             FROM CM-COMMON-MIB
    neIndex, shelfIndex, slotIndex
             FROM CM-ENTITY-MIB
    cmEthernetAccPortIndex, ShapingType, FlowVlanActionType,
    FlowTagControl, PolicerAlgorithmType, PolicerColorMode,
    cmMPFlowEntry, CmControlProtocolDispType, CmActiveControlProtocolsType,
    cmEthernetNetPortIndex, cmMPFlowIndex
             FROM CM-FACILITY-MIB
    fsp150cm
             FROM  ADVA-MIB
    ProtectLearningControl, LearningAction, FlowLearningConfigAction
             FROM F3-BRIDGE-MIB
    FlowSecState
             FROM CM-COMMON-MIB;

f3FpmMIB MODULE-IDENTITY
    LAST-UPDATED        "201607110000Z"
    ORGANIZATION    "ADVA Optical Networking SE"
    CONTACT-INFO
        "Web URL: http://adva.com/
        E-mail:  support@adva.com
        Postal:  ADVA Optical Networking SE
             Campus Martinsried
             Fraunhoferstrasse 9a
             82152 Martinsried/Munich
             Germany
        Phone: +49 089 89 06 65 0
        Fax:  +49 089 89 06 65 199 "
    DESCRIPTION
            "This module defines the Flow Point Model MIB definitions 
             used by the F3 product lines.  
             Copyright (C) ADVA."
    REVISION        "201607110000Z"
    DESCRIPTION
        "Notes from release 201607110000Z
          (1) renamed the type FlowSecureState to FlowSecState
         Notes from release 201607080000Z
          (1) added f3AccFlowpointRefConnectGuardFlowObject, f3AccFlowpointSecureBlockingControl, and 
              f3AccFlowpointSecureState to f3AccFlowpointTable
          (2) added f3NetFlowpointRefConnectGuardFlowObject, f3NetFlowpointSecureBlockingControl,
               and f3NetFlowpointSecureState to f3NetFlowpoitTable
          (3) added f3MPFlowRefConnectGuardFlowObject and f3MPFlowSecureState to f3MPFlowExtTable
         Notes from release 201504210000Z,
         (1) Ready for release FSP150CC 8.1."

    ::= {fsp150cm 43}
    
-- 
-- OID definitions
-- 

f3FpmConfigObjects            OBJECT IDENTIFIER ::= {f3FpmMIB 1}
f3FpmPerfObjects              OBJECT IDENTIFIER ::= {f3FpmMIB 2}
f3FpmPerfNotifications        OBJECT IDENTIFIER ::= {f3FpmMIB 3}
f3FpmConformance              OBJECT IDENTIFIER ::= {f3FpmMIB 4}


--
--  Acess Flow Point Table
--
f3AccFlowPointTable OBJECT-TYPE
    SYNTAX      SEQUENCE OF F3AccFlowPointEntry
    MAX-ACCESS  not-accessible
    STATUS      current
    DESCRIPTION
            "A list of entries corresponding to Access Flow Point
             for configuration purposes."
    ::= { f3FpmConfigObjects 1 }

f3AccFlowPointEntry OBJECT-TYPE
    SYNTAX      F3AccFlowPointEntry 
    MAX-ACCESS  not-accessible
    STATUS      current
    DESCRIPTION
            "A conceptual row in the f3AccFlowPointTable.
             These entries represent an Access Flow Point.
             If the Flow Point attached to a lag, the slotIndex should 
             be 255 (255 is used to identify the Flow Point belongs to lag), 
             and the cmEthernetAccPortIndex should be the f3LagIndex."
             
    INDEX { neIndex, shelfIndex, slotIndex, cmEthernetAccPortIndex, f3AccFlowPointIndex }
    ::= { f3AccFlowPointTable 1 }

F3AccFlowPointEntry ::= SEQUENCE {
    f3AccFlowPointIndex                           Integer32,
    f3AccFlowPointAlias                           DisplayString,

    f3AccFlowPointAdminState                      AdminState,
    f3AccFlowPointOperationalState                OperationalState,
    f3AccFlowPointSecondaryState                  SecondaryState,

    f3AccFlowPointAssociatedFlowId                VariablePointer,

    f3AccFlowPointIngressMultiCOSEnabled          TruthValue,
    f3AccFlowPointIngressCOS	                  Integer32,
    f3AccFlowPointEgressShapingType               ShapingType,

    f3AccFlowPointIngressVlanMemberList           DisplayString,
    f3AccFlowPointVlanMemberAction                FlowVlanActionType,
    f3AccFlowPointVlanMemberActionVlan            DisplayString,
    f3AccFlowPointIngressUntaggedFrameEnabled     TruthValue,

    f3AccFlowPointCTagControl                     FlowTagControl,
    f3AccFlowPointCTagVlanId                      VlanId,
    f3AccFlowPointCTagVlanPriority                VlanPriority,
    f3AccFlowPointSTagControl                     FlowTagControl,
    f3AccFlowPointSTagVlanId                      VlanId,
    f3AccFlowPointSTagVlanPriority                VlanPriority,
        
    f3AccFlowPointEgressOuterTagPrioMapEnabled    TruthValue,
    f3AccFlowPointEgressInnerTagPrioMapEnabled    TruthValue,
    f3AccFlowPointSESFramesLossThresholdRatio     Integer32,
    f3AccFlowPointDefaultMemberEnabled            TruthValue,
    
    f3AccFlowPointMcastRateLimitEnabled           TruthValue,
    f3AccFlowPointMcastRateLimitSpeedLo           Unsigned32,
    f3AccFlowPointMcastRateLimitSpeedHi           Unsigned32,
    f3AccFlowPointBcastRateLimitEnabled           TruthValue,
    f3AccFlowPointBcastRateLimitSpeedLo           Unsigned32,
    f3AccFlowPointBcastRateLimitSpeedHi           Unsigned32,
    f3AccFlowPointCombinedRateLimitEnabled        TruthValue,
    f3AccFlowPointCombinedRateLimitSpeedLo        Unsigned32,
    f3AccFlowPointCombinedRateLimitSpeedHi        Unsigned32,

    f3AccFlowPointSplitHorizonGroupOID            VariablePointer,
    f3AccFlowPointLoopAvoidance                   VariablePointer,
    f3AccFlowPointHierarchicalCOSEnabled          TruthValue,
    f3AccFlowPointMaximumBWLo                     Unsigned32,
    f3AccFlowPointMaximumBWHi                     Unsigned32,
    f3AccFlowPointGuaranteedBWLo                  Unsigned32,
    f3AccFlowPointGuaranteedBWHi                  Unsigned32,
    f3AccFlowPointAutoBandwidthConfigEnabled      TruthValue,
    f3AccFlowPointAutoCIRPercentage               Integer32,
    f3AccFlowPointFrameFwdEnabled                 TruthValue,

    f3AccFlowPointStorageType                     StorageType,
    f3AccFlowPointRowStatus                       RowStatus,

    f3AccFlowPointUsePortPrioMapProfile           TruthValue,
    f3AccFlowPointRefPrioMapProfile               VariablePointer,
    f3AccFlowpointRefConnectGuardFlowObject       VariablePointer,
    f3AccFlowpointSecureBlockingControl           TruthValue,
    f3AccFlowpointSecureState                     FlowSecState,
    
    f3AccFlowPointElmiEvcIdentifier               DisplayString
}

f3AccFlowPointIndex OBJECT-TYPE
    SYNTAX      Integer32 (1..65535)
    MAX-ACCESS  not-accessible
    STATUS      current
    DESCRIPTION
       "The integer index value corresponding to an Flow Point." 
    ::= { f3AccFlowPointEntry 1 }

f3AccFlowPointAlias OBJECT-TYPE
    SYNTAX      DisplayString (SIZE(0..64))
    MAX-ACCESS  read-create
    STATUS      current
    DESCRIPTION
       "This object allows SNMP management entities to provide a
        circuit identifier with the Flow Point."
    ::= { f3AccFlowPointEntry 2 }

f3AccFlowPointAdminState OBJECT-TYPE
    SYNTAX      AdminState 
    MAX-ACCESS  read-create
    STATUS      current
    DESCRIPTION
       "This object represents the Administrative State of the Flow Point." 
    ::= { f3AccFlowPointEntry 3 }

f3AccFlowPointOperationalState OBJECT-TYPE
    SYNTAX      OperationalState 
    MAX-ACCESS  read-only
    STATUS      current
    DESCRIPTION
       "This object represents the Operational State of the Flow Point." 
    ::= { f3AccFlowPointEntry 4 }

f3AccFlowPointSecondaryState OBJECT-TYPE
    SYNTAX      SecondaryState 
    MAX-ACCESS  read-only
    STATUS      current
    DESCRIPTION
       "This object represents the Secondary State of the Flow Point." 
    ::= { f3AccFlowPointEntry 5 }

f3AccFlowPointAssociatedFlowId OBJECT-TYPE
    SYNTAX      VariablePointer
    MAX-ACCESS  read-only
    STATUS      current
    DESCRIPTION
       "This object provides the association of an Flow with an Flow Point."
    ::= { f3AccFlowPointEntry 6 }

f3AccFlowPointIngressMultiCOSEnabled OBJECT-TYPE
    SYNTAX     TruthValue
    MAX-ACCESS read-create
    STATUS     current
    DESCRIPTION
       "This object allows specification of ingress multiple COS
       (Class of Service) Flow Point." 
    ::= { f3AccFlowPointEntry 7 }

f3AccFlowPointIngressCOS OBJECT-TYPE
    SYNTAX     Integer32
    MAX-ACCESS read-create
    STATUS     deprecated
    DESCRIPTION
       "This object allows specification of ingress COS 
       (Class of Service) Flow Point. 

       This attribute has been deprecated and is not supported. The
       Ingress COS is determined from the flowpoint's associated
       Priority Mapping Profle."
    ::= { f3AccFlowPointEntry 8 }
     
f3AccFlowPointEgressShapingType OBJECT-TYPE
    SYNTAX     ShapingType
    MAX-ACCESS read-write
    STATUS     current
    DESCRIPTION
       "This object allows specification of Shaping Type for Flow Point.
        For 8.1.1 release, only flow-based Shaping Type is supported." 
    ::= { f3AccFlowPointEntry 9 }

f3AccFlowPointIngressVlanMemberList OBJECT-TYPE
    SYNTAX     DisplayString (SIZE (0..512))
    MAX-ACCESS read-create
    STATUS     current
    DESCRIPTION
       "It allows specification of VLAN members of the Flow Point.
        VLAN members are comma separated, of the form X-Y where X is the
        VLAN Id and Y is the VLAN Priority. VLAN members can be of
        the form X-* or X (vlan X with all priorities), *-Y (all vlans
        with priority Y), and X1:X2 (range of vlans from X1 to X2, 
        all priorities). Members with specific VLAN Id and specific
        VLAN Priority are not supported. Once the Flow Point is created,
        this attribute can only be updated using f3AccFlowPointVlanMemberAction
        and f3AccFlowPointVlanMemberActionVlan objects."
    ::= { f3AccFlowPointEntry 10 }

f3AccFlowPointVlanMemberAction OBJECT-TYPE
    SYNTAX     FlowVlanActionType 
    MAX-ACCESS read-write
    STATUS     current
    DESCRIPTION
       "This object allows to add or remove the VLAN members specified by
        f3AccFlowPointVlanMemberActionVlan object. SNMP manager must first
        configure the VLAN member to be added/removed in the object
        f3AccFlowPointVlanMemberActionVlan and then should specify
        f3AccFlowPointVlanMemberAction on whether to add/remove the specified
        VLAN member."
    ::= { f3AccFlowPointEntry 11 }

f3AccFlowPointVlanMemberActionVlan OBJECT-TYPE
    SYNTAX     DisplayString (SIZE (0..16))
    MAX-ACCESS read-create
    STATUS     current
    DESCRIPTION
       "This object allows adding/removing VLAN members to a Flow Point.
        VLAN member is of the form X-Y where X is the VLAN Id and Y is
        the VLAN Priority. VLAN members can be of the form X-* (vlan X 
        with all priorities), *-Y (all vlans with priority Y), and X1:X2 
        (range of vlans from X1 to X2, all priorities). Members with 
        specific VLAN Id and specific VLAN Priority are not supported.
        In order to add/remove VLAN member to a flow, user must specify
        this object with appropriate VLAN and then 
        invoke f3AccFlowPointVlanMemberAction."
    ::= { f3AccFlowPointEntry 12 }
     
f3AccFlowPointIngressUntaggedFrameEnabled OBJECT-TYPE
    SYNTAX     TruthValue 
    MAX-ACCESS read-create
    STATUS     current
    DESCRIPTION
       "This object allows to specify whether or not the Flow Point
        supports untagged frame."
    ::= { f3AccFlowPointEntry 13 }

f3AccFlowPointCTagControl OBJECT-TYPE
    SYNTAX     FlowTagControl
    MAX-ACCESS read-create
    STATUS     current
    DESCRIPTION
       "This object allows specification of the tag management 
        operation on the C-TAG.  Supported types are 'push', 'pushvid',
        'swaptag', 'swapvid' and 'none'. If the type is 'push',
        the VLAN Id (f3AccFlowPointCTagVlanId) and priority
        (f3AccFlowPointCTagVlanPriority) are pushed onto the frame;
        if the type is 'pushvid', only the VLAN Id (12 bits) is pushed,
        the Priority is copied from incoming tag's priority;
        if the type is 'swaptag', both VLAN Id and Priority (15 bits)
        are swapped with the specified f3AccFlowPointCTagVlanId and 
        f3AccFlowPointCTagVlanPriority;
        if the type is 'swapvid', only the VLAN Id (12 bits) are 
        swapped with the specified f3AccFlowPointCTagVlanId; 
        if the type is 'none', no C-TAG management is performed."
    ::= { f3AccFlowPointEntry 14 }

f3AccFlowPointCTagVlanId OBJECT-TYPE
    SYNTAX     VlanId
    MAX-ACCESS read-create
    STATUS     current
    DESCRIPTION
       "This object allows specification of the VLAN Id to
        be pushed or swapped, based on the value of 
        f3AccFlowPointIngressCTagControl. It is applicable 
        for 'push', 'swaptag', 'swapvid' and 'pushvid' control types."
    ::= { f3AccFlowPointEntry 15 }

f3AccFlowPointCTagVlanPriority OBJECT-TYPE
    SYNTAX     VlanPriority
    MAX-ACCESS read-create
    STATUS     current
    DESCRIPTION
       "This object allows specification of the VLAN Priority to
        be pushed or swapped, based on the value of f3AccFlowPointIngressCTagControl.
        It is applicable for 'push' and 'swaptag' control types."
    ::= { f3AccFlowPointEntry 16 }
     
f3AccFlowPointSTagControl OBJECT-TYPE
    SYNTAX     FlowTagControl
    MAX-ACCESS read-create
    STATUS     current
    DESCRIPTION
       "This object allows specification of the tag management 
        operation on the S-TAG.  Supported types are 'push', 'pushvid',
        'swaptag', 'swapvid' and 'none'. If the type is 'push', 
        the VLAN Id (f3AccFlowPointSTagVlanId) and priority
        (f3AccFlowPointSTagVlanPriority) are pushed onto the frame;
        if the type is 'pushvid', only the VLAN Id (12 bits) is pushed,
        the Priority is copied from incoming tag's priority;
        if the type is 'swaptag', both VLAN Id and Priority (15 bits) 
        are swapped with the specified f3AccFlowPointSTagVlanId and 
        f3AccFlowPointSTagVlanPriority;
        if the type is 'swapvid', only the VLAN Id (12 bits) are 
        swapped with the specified f3AccFlowPointSTagVlanId; 
        if the type is 'none', no S-TAG management is performed."
    ::= { f3AccFlowPointEntry 17 }

f3AccFlowPointSTagVlanId OBJECT-TYPE
    SYNTAX     VlanId
    MAX-ACCESS read-create
    STATUS     current
    DESCRIPTION
       "This object allows specification of the VLAN Id to
        be pushed or swapped, based on the value of 
        f3AccFlowPointIngressSTagControl. It is applicable 
        for 'push', 'swaptag', 'swapvid' and 'pushvid' control types."
    ::= { f3AccFlowPointEntry 18 }

f3AccFlowPointSTagVlanPriority OBJECT-TYPE
    SYNTAX     VlanPriority
    MAX-ACCESS read-create
    STATUS     current
    DESCRIPTION
       "This object allows specification of the VLAN Priority to
        be pushed or swapped, based on the value of 
        f3AccFlowPointIngressSTagControl. It is applicable
        for 'push' and 'swaptag' control types."
    ::= { f3AccFlowPointEntry 19 }
     
f3AccFlowPointEgressOuterTagPrioMapEnabled OBJECT-TYPE
    SYNTAX     TruthValue
    MAX-ACCESS read-create
    STATUS     current
    DESCRIPTION
       "This object defines whether to use the Egress Prio 
        Mapping to swap the priority of outer tag. When Enabled,
        it indicates that the operation specified in the 
        EgressPrioMapTable would be applied to Flow for specified COS.
        When Disabled,the EgressPrioMapTable operations are ignored 
        for specified Flow COS."
    ::= { f3AccFlowPointEntry 20 }

f3AccFlowPointEgressInnerTagPrioMapEnabled OBJECT-TYPE
    SYNTAX     TruthValue
    MAX-ACCESS read-create
    STATUS     current
    DESCRIPTION
       "This object defines whether to use the Egress Prio
        Mapping to swap the priority of inner tag. When Enabled,
        it indicates that the operation specified in the 
        EgressPrioMapTable would be applied to Flow for specified COS.
        When Disabled, the EgressPrioMapTable operations are ignored
        for specified Flow COS."
    ::= { f3AccFlowPointEntry 21 }

f3AccFlowPointSESFramesLossThresholdRatio OBJECT-TYPE 
    SYNTAX     Integer32 (0..100)
    MAX-ACCESS read-create
    STATUS     current
    DESCRIPTION
       "This object is used to specify the frame-loss ratio 
        per flow that starts counting Severely Errored Seconds (SES) 
        on the flowpoint.
        This functionality is applicable if the flowpoint is monitored
        using the Y.1731 ESA functionality." 
    ::= { f3AccFlowPointEntry 22 }

f3AccFlowPointDefaultMemberEnabled OBJECT-TYPE
    SYNTAX      TruthValue
    MAX-ACCESS  read-create
    STATUS      current
    DESCRIPTION
       "Truth Value means that on this FP, the membership is all the tag
        packets without match any other membership associated to the port.
        Untagged means untagged flow. Default only care tagged flow."
    ::= { f3AccFlowPointEntry 23 }

f3AccFlowPointMcastRateLimitEnabled OBJECT-TYPE
    SYNTAX      TruthValue
    MAX-ACCESS  read-create
    STATUS      current
    DESCRIPTION
       "Whether multicast packets need be limited per FP." 
    ::= { f3AccFlowPointEntry 24 }

f3AccFlowPointMcastRateLimitSpeedLo OBJECT-TYPE
    SYNTAX      Unsigned32
    MAX-ACCESS  read-create
    STATUS      current
    DESCRIPTION
       "The rate limiting for multicast packets per FP. When
        f3AccFlowPointMcastRateLimitEnabled and the value is 0,
        it means all multicast frame are dropped. This objects
        only represents low 32 bits."
    ::= { f3AccFlowPointEntry 25 }

f3AccFlowPointMcastRateLimitSpeedHi OBJECT-TYPE
    SYNTAX      Unsigned32
    MAX-ACCESS  read-create
    STATUS      current
    DESCRIPTION
       "The rate limiting for multicast packets per FP. When
        f3AccFlowPointMcastRateLimitEnabled and the value is 0, 
        it means all multicast frame are dropped. This objects
        only represents high 32 bits." 
    ::= { f3AccFlowPointEntry 26 }

f3AccFlowPointBcastRateLimitEnabled OBJECT-TYPE
    SYNTAX      TruthValue
    MAX-ACCESS  read-create
    STATUS      current
    DESCRIPTION
       "Whether broadcast packets need be limited per FP." 
    ::= { f3AccFlowPointEntry 27 }

f3AccFlowPointBcastRateLimitSpeedLo OBJECT-TYPE
    SYNTAX      Unsigned32
    MAX-ACCESS  read-create
    STATUS      current
    DESCRIPTION
       "The rate limiting for broadcast packets per FP. When
        f3AccFlowPointBcastRateLimitEnabled and the value is 0, 
        it means all multicast frame are dropped. This objects
        only represents low 32 bits." 
    ::= { f3AccFlowPointEntry 28 }

f3AccFlowPointBcastRateLimitSpeedHi OBJECT-TYPE
    SYNTAX      Unsigned32
    MAX-ACCESS  read-create
    STATUS      current
    DESCRIPTION
       "The rate limiting for broadcast packets per FP. When 
        f3AccFlowPointBcastRateLimitEnabled and the value is 0, 
        it means all multicast frame are dropped. This objects
        only represents high 32 bits."
    ::= { f3AccFlowPointEntry 29 }

f3AccFlowPointCombinedRateLimitEnabled OBJECT-TYPE
    SYNTAX      TruthValue
    MAX-ACCESS  read-create
    STATUS      current
    DESCRIPTION
       "Whether broadcast and multicast packets need be limited per FP." 
    ::= { f3AccFlowPointEntry 30 }

f3AccFlowPointCombinedRateLimitSpeedLo OBJECT-TYPE
    SYNTAX      Unsigned32
    MAX-ACCESS  read-create
    STATUS      current
    DESCRIPTION
       "The rate limiting for broadcast and multicast packets per FP.
        When f3AccFlowPointCombinedRateLimitEnabled is true and the value is 0, 
        it means all broadcast and multicast frame are dropped. This object
        only represents low 32 bits." 
    ::= { f3AccFlowPointEntry 31 }

f3AccFlowPointCombinedRateLimitSpeedHi OBJECT-TYPE
    SYNTAX      Unsigned32
    MAX-ACCESS  read-create
    STATUS      current
    DESCRIPTION
       "The rate limiting for broadcast and multicast packets per FP.
        When f3AccFlowPointCombinedRateLimitEnabled is true and the value is 0, 
        it means all broadcast and multicast frame are dropped. This object
        only represents high 32 bits." 
    ::= { f3AccFlowPointEntry 32 }

f3AccFlowPointSplitHorizonGroupOID OBJECT-TYPE
    SYNTAX      VariablePointer
    MAX-ACCESS  read-create
    STATUS      current
    DESCRIPTION
       "Specifies the Split-Horizon Group OID. If there is no SHG, the value is none." 
    ::= { f3AccFlowPointEntry 33 }

f3AccFlowPointLoopAvoidance OBJECT-TYPE
    SYNTAX      VariablePointer
    MAX-ACCESS  read-create
    STATUS      current
    DESCRIPTION
       "EID of this associated Loop Avoidance protocol entity.
        A value of NONE indicates there is no loop avoidance protocol.
        Currently ERP EID is filled when ELAN service is created." 
    ::= { f3AccFlowPointEntry 34 }

f3AccFlowPointHierarchicalCOSEnabled OBJECT-TYPE
    SYNTAX      TruthValue
    MAX-ACCESS  read-create
    STATUS      current
    DESCRIPTION
       "Enable or Disable Hierarchical COS shaping (flow shaping)." 
    ::= { f3AccFlowPointEntry 35 }

f3AccFlowPointMaximumBWLo OBJECT-TYPE
    SYNTAX      Unsigned32
    MAX-ACCESS  read-create
    STATUS      current
    DESCRIPTION
       "This attribute description the Flow Point maximum bandwidth.
        This object only represents low 32 bits." 
    ::= { f3AccFlowPointEntry 36 }

f3AccFlowPointMaximumBWHi OBJECT-TYPE
    SYNTAX      Unsigned32
    MAX-ACCESS  read-create
    STATUS      current
    DESCRIPTION
       "This attribute description the Flow Point maximum bandwidth.
        This object only represents high 32 bits." 
    ::= { f3AccFlowPointEntry 37 }

f3AccFlowPointGuaranteedBWLo OBJECT-TYPE
    SYNTAX      Unsigned32
    MAX-ACCESS  read-create
    STATUS      current
    DESCRIPTION
       "This attribute description the Flow Point guaranteed bandwidth.
        This object only represents low 32 bits." 
    ::= { f3AccFlowPointEntry 38 }

f3AccFlowPointGuaranteedBWHi OBJECT-TYPE
    SYNTAX      Unsigned32
    MAX-ACCESS  read-create
    STATUS      current
    DESCRIPTION
       "This attribute description the Flow Point guaranteed bandwidth.
        This objects only represents high 32 bits." 
    ::= { f3AccFlowPointEntry 39 }
    
f3AccFlowPointAutoBandwidthConfigEnabled OBJECT-TYPE
    SYNTAX      TruthValue
    MAX-ACCESS  read-create
    STATUS      current
    DESCRIPTION
       "This object specifies the shaper bandwidth is automatically adjusted 
        by the system. For a single COS Flow Point, the shaper EIR bandwidth is 
        set to the maximum port bandwidth; the shaper CIR is set to the available 
        port bandwidth multiplied by the value of the f3AccFlowPointAutoCIRPercentage
        object. For a Hierarchical-COS Flow Point, the f3AccFlowPointMaximumBWLo and
        f3AccFlowPointMaximumBWHi are set to the maximum port bandwidth; 
        the f3AccFlowPointGuaranteedBWLo and f3AccFlowPointGuaranteedBWHi are set to 
        the available port bandwidth multiplied by the value of the 
        f3AccFlowPointAutoCIRPercentage object. The value of this object must be FALSE 
        when f3AccFlowPointIngressMultiCOSEnabled is TRUE and 
        f3AccFlowPointHierarchicalCOSEnabled is FALSE." 
    ::= { f3AccFlowPointEntry 40 }
    
f3AccFlowPointAutoCIRPercentage OBJECT-TYPE
    SYNTAX      Integer32 (0..100)
    MAX-ACCESS  read-create
    STATUS      current
    DESCRIPTION
       "This object specifies the percentage of available shaper CIR to be assigned 
        to this Flow Point when f3AccFlowPointAutoBandwidthConfigEnabled is TRUE." 
    ::= { f3AccFlowPointEntry 41 }

f3AccFlowPointFrameFwdEnabled OBJECT-TYPE
    SYNTAX      TruthValue
    MAX-ACCESS  read-create
    STATUS      current
    DESCRIPTION
       "When enabled Flow Point will forward frames it receives. When disabled, 
        the Flow Point will not forward frames it receives." 
    ::= { f3AccFlowPointEntry 42 }

f3AccFlowPointStorageType OBJECT-TYPE
    SYNTAX     StorageType
    MAX-ACCESS read-create
    STATUS     current
    DESCRIPTION
       "The type of storage configured for this entry."
    ::= { f3AccFlowPointEntry 43 }

f3AccFlowPointRowStatus OBJECT-TYPE
    SYNTAX      RowStatus
    MAX-ACCESS  read-create
    STATUS      current
    DESCRIPTION
       "The status of this row.
        An entry MUST NOT exist in the active state unless all
        objects in the entry have an appropriate value, as described
        in the description clause for each writable object.

        The values of f3AccFlowPointRowStatus supported are
        createAndGo(4) and destroy(6).  All mandatory attributes
        must be specified in a single SNMP SET request with
        f3AccFlowPointRowStatus value as createAndGo(4).
        Upon successful row creation, this object has a
        value of active(1).

        The f3AccFlowPointRowStatus object may be modified if
        the associated instance of this object is equal to active(1)."
    ::= { f3AccFlowPointEntry 44 }

f3AccFlowPointUsePortPrioMapProfile OBJECT-TYPE
    SYNTAX      TruthValue  
    MAX-ACCESS  read-write
    STATUS      current
    DESCRIPTION
         "This indicates whether the flow point is using, if true, the port's 
         Priority Mapping Profile or, if false, is using its own
         Priority Mapping Profile."
    ::= { f3AccFlowPointEntry 45 }

f3AccFlowPointRefPrioMapProfile OBJECT-TYPE
    SYNTAX      VariablePointer  
    MAX-ACCESS  read-write
    STATUS      current
    DESCRIPTION
         "This object allows to set priority map profile."
    ::= { f3AccFlowPointEntry 46 }

f3AccFlowpointRefConnectGuardFlowObject OBJECT-TYPE
    SYNTAX     VariablePointer
    MAX-ACCESS read-write
    STATUS     current
    DESCRIPTION
          "This object specifies Mac Sec flow object OID."
     ::= { f3AccFlowPointEntry 47 }

f3AccFlowpointSecureBlockingControl OBJECT-TYPE
    SYNTAX     TruthValue
    MAX-ACCESS read-write
    STATUS     current
    DESCRIPTION
          "This object can be used to enable/disable secure block."
     ::= { f3AccFlowPointEntry 48 }

f3AccFlowpointSecureState OBJECT-TYPE
    SYNTAX     FlowSecState
    MAX-ACCESS read-only
    STATUS     current
    DESCRIPTION
          "This object specifies the secure state of this flow."
     ::= { f3AccFlowPointEntry 49 }
     
f3AccFlowPointElmiEvcIdentifier OBJECT-TYPE
    SYNTAX      DisplayString  
    MAX-ACCESS  read-create
    STATUS      current
    DESCRIPTION
         "This object specifies Access FlowPoint Evc Identifier 
          required for E-LMI feature."
    ::= { f3AccFlowPointEntry 50 }

--
--  Access Flow Point QoS Shaper
--
f3AccFpQosShaperTable OBJECT-TYPE
    SYNTAX      SEQUENCE OF F3AccFpQosShaperEntry
    MAX-ACCESS  not-accessible
    STATUS      current
    DESCRIPTION
       "A list of entries corresponding to Access Flow Point 
        Quality of Service Shaper for configuration purposes."
    ::= { f3FpmConfigObjects 2 }

f3AccFpQosShaperEntry OBJECT-TYPE
    SYNTAX      F3AccFpQosShaperEntry 
    MAX-ACCESS  not-accessible
    STATUS      current
    DESCRIPTION
       "A conceptual row in the f3AccFpQosShaperTable. 
        These entries represent an Access Flow Point Quality 
        of Service Shaper."
    INDEX { neIndex, shelfIndex, slotIndex, cmEthernetAccPortIndex, 
            f3AccFlowPointIndex, f3AccFpQosShaperIndex }
    ::= { f3AccFpQosShaperTable 1 }

F3AccFpQosShaperEntry ::= SEQUENCE {
    f3AccFpQosShaperIndex               Integer32,

    f3AccFpQosShaperAdminState          AdminState,
    f3AccFpQosShaperOperationalState    OperationalState,
    f3AccFpQosShaperSecondaryState      SecondaryState,

    f3AccFpQosShaperCIRLo               Unsigned32,
    f3AccFpQosShaperCIRHi               Unsigned32,
    f3AccFpQosShaperEIRLo               Unsigned32,
    f3AccFpQosShaperEIRHi               Unsigned32,
    f3AccFpQosShaperCBS                 Unsigned32,
    f3AccFpQosShaperEBS                 Unsigned32,
    f3AccFpQosShaperBufferSize          Unsigned32,
    f3AccFpQosShaperCOS                 Integer32,
    
    f3AccFpQosShaperStorageType         StorageType,
    f3AccFpQosShaperRowStatus           RowStatus
}

f3AccFpQosShaperIndex OBJECT-TYPE
    SYNTAX      Integer32 (1..8)
    MAX-ACCESS  not-accessible
    STATUS      current
    DESCRIPTION
       "The unique integer index value corresponding to a Quality 
        of Service Shaper."
    ::= { f3AccFpQosShaperEntry 1 }

f3AccFpQosShaperAdminState OBJECT-TYPE
    SYNTAX      AdminState 
    MAX-ACCESS  read-create
    STATUS      current
    DESCRIPTION
       "This object represents the Administrative State of a Shaper." 
    ::= { f3AccFpQosShaperEntry 2 }

f3AccFpQosShaperOperationalState OBJECT-TYPE
    SYNTAX      OperationalState 
    MAX-ACCESS  read-only
    STATUS      current
    DESCRIPTION
       "This object represents the Operational State of a Shaper." 
    ::= { f3AccFpQosShaperEntry 3 }

f3AccFpQosShaperSecondaryState OBJECT-TYPE
    SYNTAX      SecondaryState 
    MAX-ACCESS  read-only
    STATUS      current
    DESCRIPTION
       "This object represents the Secondary State of the Shaper." 
    ::= { f3AccFpQosShaperEntry 4 }

f3AccFpQosShaperCIRLo OBJECT-TYPE
    SYNTAX      Unsigned32
    MAX-ACCESS  read-create
    STATUS      current
    DESCRIPTION
       "This object represents the Commited Information Rate (CIR)
        (Lower 32 bits) of the Shaper."
    ::= { f3AccFpQosShaperEntry 5 }
     
f3AccFpQosShaperCIRHi OBJECT-TYPE
    SYNTAX      Unsigned32
    MAX-ACCESS  read-create
    STATUS      current
    DESCRIPTION
       "This object represents the Commited Information Rate (CIR)
        (Higher 32 bits) of the Shaper."
    ::= { f3AccFpQosShaperEntry 6 }

f3AccFpQosShaperEIRLo OBJECT-TYPE
    SYNTAX      Unsigned32
    MAX-ACCESS  read-create
    STATUS      current
    DESCRIPTION
       "This object represents the Excess Information Rate (EIR)
        (Lower 32 bits) of a Shaper."
    ::= { f3AccFpQosShaperEntry 7 }

f3AccFpQosShaperEIRHi OBJECT-TYPE
    SYNTAX      Unsigned32
    MAX-ACCESS  read-create
    STATUS      current
    DESCRIPTION
       "This object represents the Excess Information Rate (EIR)
        (Lower 32 bits) of a Shaper."
    ::= { f3AccFpQosShaperEntry 8 }

f3AccFpQosShaperCBS OBJECT-TYPE
    SYNTAX      Unsigned32
    MAX-ACCESS  read-create
    STATUS      current
    DESCRIPTION
       "This object represents the Commited Burst Size (CBS) 
        of a Shaper."
    ::= { f3AccFpQosShaperEntry 9 }

f3AccFpQosShaperEBS OBJECT-TYPE
    SYNTAX      Unsigned32
    MAX-ACCESS  read-create
    STATUS      current
    DESCRIPTION
       "This object represents the Excess Burst Size (EBS) 
        of a Shaper."
    ::= { f3AccFpQosShaperEntry 10 }

f3AccFpQosShaperBufferSize OBJECT-TYPE
    SYNTAX      Unsigned32
    MAX-ACCESS  read-create
    STATUS      current
    DESCRIPTION
       "This object represents the Buffer Size of the Shaper."
    ::= { f3AccFpQosShaperEntry 11 }

f3AccFpQosShaperCOS OBJECT-TYPE
    SYNTAX      Integer32 (0..7)
    MAX-ACCESS  read-only
    STATUS      current
    DESCRIPTION
       "This object provides the COS (Class of Service) value for
        the QOS Shaper."
    ::= { f3AccFpQosShaperEntry 12 }

f3AccFpQosShaperStorageType OBJECT-TYPE
    SYNTAX      StorageType
    MAX-ACCESS  read-create
    STATUS      current
    DESCRIPTION
       "The type of storage configured for this entry."
    ::= { f3AccFpQosShaperEntry 13 }

f3AccFpQosShaperRowStatus OBJECT-TYPE
    SYNTAX      RowStatus
    MAX-ACCESS  read-create
    STATUS      current
    DESCRIPTION
       "The status of this row.
        An entry MUST NOT exist in the active state unless all
        objects in the entry have an appropriate value, as described
        in the description clause for each writable object.

        The values of f3AccFpQosShaperRowStatus supported are
        createAndGo(4) and destroy(6). All mandatory attributes
        must be specified in a single SNMP SET request with
        f3AccFpQosShaperRowStatus value as createAndGo(4).
        Upon successful row creation, this object has a
        value of active(1).

        The f3AccFpQosShaperRowStatus object may be modified if
        the associated instance of this object is equal to active(1)."
    ::= { f3AccFpQosShaperEntry 14 }

--
--  Access Flow Point QoS Policer
--
f3AccFpQosPolicerTable  OBJECT-TYPE
    SYNTAX      SEQUENCE OF F3AccFpQosPolicerEntry
    MAX-ACCESS  not-accessible
    STATUS      current
    DESCRIPTION
       "A list of entries corresponding to Access Flow Point
        Quality of Service Policer for configuration purposes."
    ::= { f3FpmConfigObjects 3 }

f3AccFpQosPolicerEntry OBJECT-TYPE
    SYNTAX      F3AccFpQosPolicerEntry 
    MAX-ACCESS  not-accessible
    STATUS      current
    DESCRIPTION
       "A conceptual row in the f3AccFpQosPolicerTable. 
        These entries represent an Access Flow Point Quality
        of Service Policer."
    INDEX { neIndex, shelfIndex, slotIndex, cmEthernetAccPortIndex, 
            f3AccFlowPointIndex, f3AccFpQosPolicerIndex }
    ::= { f3AccFpQosPolicerTable 1 }

F3AccFpQosPolicerEntry ::= SEQUENCE {
    f3AccFpQosPolicerIndex                 Integer32,

    f3AccFpQosPolicerAdminState            AdminState,
    f3AccFpQosPolicerOperationalState      OperationalState,
    f3AccFpQosPolicerSecondaryState        SecondaryState,

    f3AccFpQosPolicerCIRLo                 Unsigned32,
    f3AccFpQosPolicerCIRHi                 Unsigned32,
    f3AccFpQosPolicerEIRLo                 Unsigned32,
    f3AccFpQosPolicerEIRHi                 Unsigned32,
    f3AccFpQosPolicerCBS                   Integer32,
    f3AccFpQosPolicerEBS                   Integer32,
    
    f3AccFpQosPolicerAlgorithm             PolicerAlgorithmType,
    f3AccFpQosPolicerColorMode             PolicerColorMode,
    f3AccFpQosPolicerCouplingFlag          TruthValue,
    f3AccFpQosPolicerPolicingEnabled       TruthValue,
    
    f3AccFpQosPolicerStorageType           StorageType,
    f3AccFpQosPolicerRowStatus             RowStatus 
}

f3AccFpQosPolicerIndex OBJECT-TYPE
    SYNTAX      Integer32 (1..8)
    MAX-ACCESS  not-accessible
    STATUS      current
    DESCRIPTION
       "The unique integer index value corresponding to a Quality 
        of Service Policer.
        The Policer Index represents the COS level. This
        is applicable in case of a Multi COS Flow Point. Index 1
        represents COS 0; Index 2 represents COS 1 and so on."
    ::= { f3AccFpQosPolicerEntry 1 }

f3AccFpQosPolicerAdminState OBJECT-TYPE
    SYNTAX      AdminState 
    MAX-ACCESS  read-create
    STATUS      current
    DESCRIPTION
       "This object represents the Administrative State of a Policer."
    ::= { f3AccFpQosPolicerEntry 2 }

f3AccFpQosPolicerOperationalState OBJECT-TYPE
    SYNTAX      OperationalState 
    MAX-ACCESS  read-only
    STATUS      current
    DESCRIPTION
       "This object represents the Operational State of a Policer." 
    ::= { f3AccFpQosPolicerEntry 3 }

f3AccFpQosPolicerSecondaryState OBJECT-TYPE
    SYNTAX      SecondaryState 
    MAX-ACCESS  read-only
    STATUS      current
    DESCRIPTION
       "This object represents the Secondary State of a Policer." 
    ::= { f3AccFpQosPolicerEntry 4 }

f3AccFpQosPolicerCIRLo OBJECT-TYPE
    SYNTAX      Unsigned32
    MAX-ACCESS  read-create
    STATUS      current
    DESCRIPTION
       "This object represents the Commited Information Rate (CIR)
        (Lower 32 bits) of the Policer."
    ::= { f3AccFpQosPolicerEntry 5 }

f3AccFpQosPolicerCIRHi OBJECT-TYPE
    SYNTAX      Unsigned32
    MAX-ACCESS  read-create
    STATUS      current
    DESCRIPTION
       "This object represents the Commited Information Rate (CIR)
        (Higher 32 bits) of the Policer."
    ::= { f3AccFpQosPolicerEntry 6 }

f3AccFpQosPolicerEIRLo OBJECT-TYPE
    SYNTAX      Unsigned32
    MAX-ACCESS  read-create
    STATUS      current
    DESCRIPTION
       "This object represents the Excess Information Rate (EIR)
        (Lower 32 bits) of a Policer."
    ::= { f3AccFpQosPolicerEntry 7 }

f3AccFpQosPolicerEIRHi OBJECT-TYPE
    SYNTAX      Unsigned32
    MAX-ACCESS  read-create
    STATUS      current
    DESCRIPTION
       "This object represents the Excess Information Rate (EIR)
        (Lower 32 bits) of a Policer."
    ::= { f3AccFpQosPolicerEntry 8 }

f3AccFpQosPolicerCBS OBJECT-TYPE
    SYNTAX      Integer32
    MAX-ACCESS  read-create
    STATUS      current
    DESCRIPTION
       "This object represents the Commited Burst Size (CBS) 
        of a Policer."
    ::= { f3AccFpQosPolicerEntry 9 }

f3AccFpQosPolicerEBS OBJECT-TYPE
    SYNTAX      Integer32
    MAX-ACCESS  read-create
    STATUS      current
    DESCRIPTION
       "This object represents the Excess Burst Size (EBS) 
        of a Policer."
    ::= { f3AccFpQosPolicerEntry 10 }

f3AccFpQosPolicerAlgorithm OBJECT-TYPE
    SYNTAX      PolicerAlgorithmType 
    MAX-ACCESS  read-only
    STATUS      current
    DESCRIPTION
       "This object represents Policer algorithm as 'srTCM'
        (Single Rate Triple Color Marking) or 'trTCM' 
        (Two Rate Triple Color Marking)."
    ::= { f3AccFpQosPolicerEntry 11 }

f3AccFpQosPolicerColorMode OBJECT-TYPE
    SYNTAX      PolicerColorMode 
    MAX-ACCESS  read-create
    STATUS      current
    DESCRIPTION
       "This object allows specification of Policer Color Mode as
        'color-aware' or 'color-blind'."
    ::= { f3AccFpQosPolicerEntry 12 }

f3AccFpQosPolicerCouplingFlag OBJECT-TYPE
    SYNTAX      TruthValue
    MAX-ACCESS  read-create
    STATUS      current
    DESCRIPTION
       "This object allows specification of Policer Coupling Flag.
        When coupling is enabled, tokens that would normally be 
        added to the C-bucket are passed to the E-bucket only once the CIR
        bucket has reached its CBS level. Therefore under this condition
        the E-bucket is being filled at the rate of CIR + EIR. 
        Normally the long term average of frames declared yellow is 
        bounded by the EIR. Coupling is a function to allow the 
        long term average of frames declared yellow to be bounded by 
        CIR + EIR. This allows a higher volume of yellow frames 
        to be delivered/received if the arrival of green marked frames 
        is low. Tokens from the E-bucket do NOT get passed to the 
        C-bucket once the EBS level has been reached.
        Enabling coupling in combination with a provisioned EIR of 0 
        allows for a single rate three color marking (srTCM) algorithm 
        to be established.  In this situation the E-bucket is filled at the 
        CIR rate in the case the C-bucket is filled to its CBS level."
    ::= { f3AccFpQosPolicerEntry 13 }

f3AccFpQosPolicerPolicingEnabled OBJECT-TYPE
    SYNTAX      TruthValue
    MAX-ACCESS  read-create
    STATUS      current
    DESCRIPTION
       "This object allows specification of Policer Policing.
        When Policing is disabled, traffic policing is bypassed. 
        When Policing is enabled, traffic policing is applied."
    ::= { f3AccFpQosPolicerEntry 14 }

f3AccFpQosPolicerStorageType OBJECT-TYPE
    SYNTAX      StorageType
    MAX-ACCESS  read-create
    STATUS      current
    DESCRIPTION
       "The type of storage configured for this entry."
    ::= { f3AccFpQosPolicerEntry 15 }

f3AccFpQosPolicerRowStatus OBJECT-TYPE
    SYNTAX      RowStatus
    MAX-ACCESS  read-create
    STATUS      current
    DESCRIPTION
       "The status of this row.
        An entry MUST NOT exist in the active state unless all
        objects in the entry have an appropriate value, as described
        in the description clause for each writable object.

        The values of f3AccFpQosPolicerRowStatus supported are
        createAndGo(4) and destroy(6). All mandatory attributes
        must be specified in a single SNMP SET request with
        f3AccFpQosPolicerRowStatus value as createAndGo(4).
        Upon successful row creation, this object has a
        value of active(1).

        The f3AccFpQosPolicerRowStatus object may be modified if
        the associated instance of this object is equal to active(1)."
    ::= { f3AccFpQosPolicerEntry 16 }

--
--  cmMPFlowTable extension for maximum forwarding table size configurations
--
f3MPFlowExtTable  OBJECT-TYPE
    SYNTAX      SEQUENCE OF F3MPFlowExtEntry
    MAX-ACCESS  not-accessible
    STATUS      current
    DESCRIPTION
       "This table extends cmMPFlowTable to provide configuration of maximum
        forwarding table size."
    ::= { f3FpmConfigObjects 4 }

f3MPFlowExtEntry  OBJECT-TYPE
    SYNTAX      F3MPFlowExtEntry   
    MAX-ACCESS  not-accessible
    STATUS      current
    DESCRIPTION
       "A conceptual row in the f3MPFlowExtTable."
    AUGMENTS { cmMPFlowEntry }
    ::= { f3MPFlowExtTable 1 }

F3MPFlowExtEntry ::= SEQUENCE {
    f3MPFlowExtMaxFwdEntries          Integer32,
    f3MPFlowRefConnectGuardFlowObject VariablePointer,
    f3MPFlowSecureState               FlowSecState   
}

f3MPFlowExtMaxFwdEntries OBJECT-TYPE
    SYNTAX        Integer32
    MAX-ACCESS    read-write
    STATUS        current
    DESCRIPTION
       "This object allows configuring the maximum number of Forwarding Entires
        for Forwarding Table of this MP Flow."
    ::= { f3MPFlowExtEntry 1 }

f3MPFlowRefConnectGuardFlowObject OBJECT-TYPE
    SYNTAX     VariablePointer
    MAX-ACCESS read-write
    STATUS     current
    DESCRIPTION
          "This object specifies Mac Sec flow object OID."
     ::= { f3MPFlowExtEntry 2 }

f3MPFlowSecureState OBJECT-TYPE
    SYNTAX     FlowSecState
    MAX-ACCESS read-only
    STATUS     current
    DESCRIPTION
          "This object specifies the secure state of the macsec flow."
     ::= { f3MPFlowExtEntry 3 }

--
--  Access Flow Point Control Protocol Disposition 
--
f3AccFlowPointCpdV2Table  OBJECT-TYPE
    SYNTAX      SEQUENCE OF F3AccFlowPointCpdV2Entry
    MAX-ACCESS  not-accessible
    STATUS      current
    DESCRIPTION
       "A list of entries corresponding to Access Flow Point
        Control Protocol Disposition V2."
    ::= { f3FpmConfigObjects 5 }

f3AccFlowPointCpdV2Entry OBJECT-TYPE
    SYNTAX      F3AccFlowPointCpdV2Entry 
    MAX-ACCESS  not-accessible
    STATUS      current
    DESCRIPTION
       "A conceptual row in the f3AccFlowPointCpdV2Table. 
        These entries represent a Control Protocol Disposition 
        filtering criteria on the Access Flow Point."
    INDEX { neIndex, shelfIndex, slotIndex, cmEthernetAccPortIndex, 
            f3AccFlowPointIndex, f3AccFlowPointCpdV2Index }
    ::= { f3AccFlowPointCpdV2Table 1 }

F3AccFlowPointCpdV2Entry ::= SEQUENCE {
    f3AccFlowPointCpdV2Index                     Integer32,
    f3AccFlowPointCpdV2IslDispType               CmControlProtocolDispType,
    f3AccFlowPointCpdV2PagpDispType              CmControlProtocolDispType,
    f3AccFlowPointCpdV2UdldDispType              CmControlProtocolDispType,
    f3AccFlowPointCpdV2CdpDispType               CmControlProtocolDispType,
    f3AccFlowPointCpdV2VtpDispType               CmControlProtocolDispType,
    f3AccFlowPointCpdV2DtpDispType               CmControlProtocolDispType,
    f3AccFlowPointCpdV2PvstpPlusDispType         CmControlProtocolDispType,
    f3AccFlowPointCpdV2UplinkFastDispType        CmControlProtocolDispType,
    f3AccFlowPointCpdV2VlanBridgeDispType        CmControlProtocolDispType,
    f3AccFlowPointCpdV2L2PTDispType              CmControlProtocolDispType,
    f3AccFlowPointCpdV2BPDUDispType              CmControlProtocolDispType,
    f3AccFlowPointCpdV2PauseDispType             CmControlProtocolDispType,
    f3AccFlowPointCpdV2LACPDispType              CmControlProtocolDispType,
    f3AccFlowPointCpdV2LACPMarkerDispType        CmControlProtocolDispType,
    f3AccFlowPointCpdV2EfmOamDispType            CmControlProtocolDispType,
    f3AccFlowPointCpdV2SSMDispType               CmControlProtocolDispType,
    f3AccFlowPointCpdV2PortAuthenDispType        CmControlProtocolDispType,
    f3AccFlowPointCpdV2LANBridgesDispType        CmControlProtocolDispType,
    f3AccFlowPointCpdV2GMRPDispType              CmControlProtocolDispType,
    f3AccFlowPointCpdV2GVRPDispType              CmControlProtocolDispType,
    f3AccFlowPointCpdV2GARPDispType              CmControlProtocolDispType,
    f3AccFlowPointCpdV2ActiveControlProtocols    CmActiveControlProtocolsType,
    f3AccFlowPointCpdV2ELMIDispType              CmControlProtocolDispType,
    f3AccFlowPointCpdV2Mac00DispType             CmControlProtocolDispType,
    f3AccFlowPointCpdV2Mac01DispType             CmControlProtocolDispType,
    f3AccFlowPointCpdV2Mac02DispType             CmControlProtocolDispType,
    f3AccFlowPointCpdV2Mac03DispType             CmControlProtocolDispType,
    f3AccFlowPointCpdV2Mac04DispType             CmControlProtocolDispType,
    f3AccFlowPointCpdV2Mac05DispType             CmControlProtocolDispType,
    f3AccFlowPointCpdV2Mac06DispType             CmControlProtocolDispType,
    f3AccFlowPointCpdV2Mac07DispType             CmControlProtocolDispType,
    f3AccFlowPointCpdV2Mac08DispType             CmControlProtocolDispType,
    f3AccFlowPointCpdV2Mac09DispType             CmControlProtocolDispType,
    f3AccFlowPointCpdV2Mac0ADispType             CmControlProtocolDispType,
    f3AccFlowPointCpdV2Mac0BDispType             CmControlProtocolDispType,
    f3AccFlowPointCpdV2Mac0CDispType             CmControlProtocolDispType,
    f3AccFlowPointCpdV2Mac0DDispType             CmControlProtocolDispType,
    f3AccFlowPointCpdV2Mac0EDispType             CmControlProtocolDispType,
    f3AccFlowPointCpdV2Mac0FDispType             CmControlProtocolDispType,
    f3AccFlowPointCpdV2NearestLLDPDispType       CmControlProtocolDispType,
    f3AccFlowPointCpdV2NonTpmrLLDPDispType       CmControlProtocolDispType,
    f3AccFlowPointCpdV2CustomerLLDPDispType      CmControlProtocolDispType
}

f3AccFlowPointCpdV2Index OBJECT-TYPE
    SYNTAX      Integer32 
    MAX-ACCESS  not-accessible
    STATUS      current
    DESCRIPTION
       "Unique Index value to access the CPD row."
    ::= { f3AccFlowPointCpdV2Entry 1 }

f3AccFlowPointCpdV2IslDispType OBJECT-TYPE
    SYNTAX      CmControlProtocolDispType 
    MAX-ACCESS  read-write
    STATUS      current
    DESCRIPTION
       "Control Protocol Disposition for ISL (Inter Switch Link).
        MAC Address (01:00:0C:00:00:00)."
    ::= { f3AccFlowPointCpdV2Entry 2 }

f3AccFlowPointCpdV2PagpDispType OBJECT-TYPE
    SYNTAX      CmControlProtocolDispType 
    MAX-ACCESS  read-write
    STATUS      current
    DESCRIPTION
       "Control Protocol Disposition for PAGP (Port Aggregation Protocol).
        MAC Address (01:00:0C:CC:CC:CC), Ethertype(0x104)."
    ::= { f3AccFlowPointCpdV2Entry 3 }

f3AccFlowPointCpdV2UdldDispType OBJECT-TYPE
    SYNTAX      CmControlProtocolDispType 
    MAX-ACCESS  read-write
    STATUS      current
    DESCRIPTION
       "Control Protocol Disposition for UDLD (Unidirectional Link Detection).
        MAC Address (01:00:0C:CC:CC:CC), Ethertype(0x111)."
    ::= { f3AccFlowPointCpdV2Entry 4 }

f3AccFlowPointCpdV2CdpDispType OBJECT-TYPE
    SYNTAX      CmControlProtocolDispType 
    MAX-ACCESS  read-write
    STATUS      current
    DESCRIPTION
       "Control Protocol Disposition for CDP (Cisco Discovery Protocol).
        MAC Address (01:00:0C:CC:CC:CC), Ethertype(0x2000)."
    ::= { f3AccFlowPointCpdV2Entry 5 }

f3AccFlowPointCpdV2VtpDispType OBJECT-TYPE
    SYNTAX      CmControlProtocolDispType 
    MAX-ACCESS  read-write
    STATUS      current
    DESCRIPTION
       "Control Protocol Disposition for VTP (VLAN Trunking Protocol).
        MAC Address (01:00:0C:CC:CC:CC), Ethertype(0x2003)."
    ::= { f3AccFlowPointCpdV2Entry 6 }

f3AccFlowPointCpdV2DtpDispType OBJECT-TYPE
    SYNTAX      CmControlProtocolDispType 
    MAX-ACCESS  read-write
    STATUS      current
    DESCRIPTION
       "Control Protocol Disposition for DTP (Dynamic Trunking).
        MAC Address (01:00:0C:CC:CC:CC), Ethertype(0x2004)."
    ::= { f3AccFlowPointCpdV2Entry 7 }

f3AccFlowPointCpdV2PvstpPlusDispType OBJECT-TYPE
    SYNTAX      CmControlProtocolDispType 
    MAX-ACCESS  read-write
    STATUS      current
    DESCRIPTION
       "Control Protocol Disposition for Spanning Tree PVSTP+.
        MAC Address (01:00:0C:CC:CC:CC), Ethertype(0x10B)."
    ::= { f3AccFlowPointCpdV2Entry 8 }

f3AccFlowPointCpdV2UplinkFastDispType OBJECT-TYPE
    SYNTAX      CmControlProtocolDispType 
    MAX-ACCESS  read-write
    STATUS      current
    DESCRIPTION
       "Control Protocol Disposition for STP UplinkFast.
        MAC Address (01:00:0C:CD:CD:CD), Ethertype(0x200A)."
    ::= { f3AccFlowPointCpdV2Entry 9 }

f3AccFlowPointCpdV2VlanBridgeDispType OBJECT-TYPE
    SYNTAX      CmControlProtocolDispType 
    MAX-ACCESS  read-write
    STATUS      current
    DESCRIPTION
       "Control Protocol Disposition for VLAN Bridge.
        MAC Address (01:00:0C:CD:CD:CE), Ethertype(0x10C)."
    ::= { f3AccFlowPointCpdV2Entry 10 }

f3AccFlowPointCpdV2L2PTDispType OBJECT-TYPE
    SYNTAX      CmControlProtocolDispType 
    MAX-ACCESS  read-write
    STATUS      current
    DESCRIPTION
       "Control Protocol Disposition for Layer 2 Protocol Tunnelling(L2PT).
        MAC Address (01:00:0C:CD:CD:D0)."
    ::= { f3AccFlowPointCpdV2Entry 11 }

f3AccFlowPointCpdV2BPDUDispType OBJECT-TYPE
    SYNTAX      CmControlProtocolDispType 
    MAX-ACCESS  read-write
    STATUS      current
    DESCRIPTION
       "Control Protocol Disposition for IEEE Spanning Tree(STP),
        MSTP (Multiple Spanning Tree) and RSTP (Rapid Reconfiguration of
        Spanning Tree). MAC Address (01:80:C2:00:00:00)."
    ::= { f3AccFlowPointCpdV2Entry 12 }

f3AccFlowPointCpdV2PauseDispType OBJECT-TYPE
    SYNTAX      CmControlProtocolDispType 
    MAX-ACCESS  read-write
    STATUS      current
    DESCRIPTION
       "Control Protocol Disposition for IEEE 802.3x Flow Control 
        (PAUSE frames)."
    ::= { f3AccFlowPointCpdV2Entry 13 }

f3AccFlowPointCpdV2LACPDispType OBJECT-TYPE
    SYNTAX      CmControlProtocolDispType 
    MAX-ACCESS  read-write
    STATUS      current
    DESCRIPTION
       "Control Protocol Disposition for 802.3ad Link Aggregation
        Protocol.
        MAC Address (01:80:C2:00:00:03), Ethertype (0x8809), Subtype(01)."
    ::= { f3AccFlowPointCpdV2Entry 14 }

f3AccFlowPointCpdV2LACPMarkerDispType OBJECT-TYPE
    SYNTAX      CmControlProtocolDispType 
    MAX-ACCESS  read-write
    STATUS      current
    DESCRIPTION
       "Control Protocol Disposition for IEEE 802.3ad Marker Protocol.
        MAC Address (01:80:C2:00:00:03), Ethertype (0x8809), Subtype(02)."
    ::= { f3AccFlowPointCpdV2Entry 15 }

f3AccFlowPointCpdV2EfmOamDispType OBJECT-TYPE
    SYNTAX      CmControlProtocolDispType 
    MAX-ACCESS  read-write
    STATUS      current
    DESCRIPTION
       "Control Protocol Disposition for IEEE 802.3ah EFM OAM.
        MAC Address (01:80:C2:00:00:03), Ethertype (0x8809), Subtype(03)."
    ::= { f3AccFlowPointCpdV2Entry 16 }

f3AccFlowPointCpdV2SSMDispType OBJECT-TYPE
    SYNTAX      CmControlProtocolDispType 
    MAX-ACCESS  read-write
    STATUS      current
    DESCRIPTION
       "Control Protocol Disposition for Sync Status Messages.
        MAC Address (01:80:C2:00:00:02), Ethertype (0x19A7), Subtype(0A)."
    ::= { f3AccFlowPointCpdV2Entry 17 }

f3AccFlowPointCpdV2PortAuthenDispType OBJECT-TYPE
    SYNTAX      CmControlProtocolDispType 
    MAX-ACCESS  read-write
    STATUS      current
    DESCRIPTION
       "Control Protocol Disposition for IEEE 802.1x Protocol.
        MAC Address (01:80:C2:00:00:03), Ethertype (0x888E)."
    ::= { f3AccFlowPointCpdV2Entry 18 }

f3AccFlowPointCpdV2LANBridgesDispType OBJECT-TYPE
    SYNTAX      CmControlProtocolDispType 
    MAX-ACCESS  read-write
    STATUS      current
    DESCRIPTION
       "Control Protocol Disposition for IEEE 802.1d LAN Bridge Managment.
        MAC Address (01:80:C2:00:00:10)."
    ::= { f3AccFlowPointCpdV2Entry 19 }

f3AccFlowPointCpdV2GMRPDispType OBJECT-TYPE
    SYNTAX      CmControlProtocolDispType 
    MAX-ACCESS  read-write
    STATUS      current
    DESCRIPTION
       "Control Protocol Disposition for GARP Multicast Registration
        Protocol. MAC Address (01:80:C2:00:00:20)."
    ::= { f3AccFlowPointCpdV2Entry 20 }

f3AccFlowPointCpdV2GVRPDispType OBJECT-TYPE
    SYNTAX      CmControlProtocolDispType 
    MAX-ACCESS  read-write
    STATUS      current
    DESCRIPTION
       "Control Protocol Disposition for GARP VLAN Registration
        Protocol. MAC Address (01:80:C2:00:00:21)."
    ::= { f3AccFlowPointCpdV2Entry 21 }

f3AccFlowPointCpdV2GARPDispType OBJECT-TYPE
    SYNTAX      CmControlProtocolDispType 
    MAX-ACCESS  read-write
    STATUS      current
    DESCRIPTION
       "Group Disposition type which includes GARP Reserved 
        MAC Address from range 01:80:C2:00:00:22 to 01:80:C2:00:00:2F."
    ::= { f3AccFlowPointCpdV2Entry 22 }

f3AccFlowPointCpdV2ActiveControlProtocols OBJECT-TYPE
    SYNTAX      CmActiveControlProtocolsType
    MAX-ACCESS  read-only
    STATUS      current
    DESCRIPTION
       "List of Active Control Protocol Dispositions. Note that
        if the Port Level Disposition control is set to PEER or 
        DISCARD, the flow level disposition is no longer active.
        This object provides information on all the active
        dispositions."
    ::= { f3AccFlowPointCpdV2Entry 23 }

f3AccFlowPointCpdV2ELMIDispType OBJECT-TYPE
    SYNTAX      CmControlProtocolDispType 
    MAX-ACCESS  read-write
    STATUS      current
    DESCRIPTION
       "ELMI (Ethernet Local Management Interface) Disposition type. 
        MAC Address 01:80:C2:00:00:07 and EtherType of 0x88EE."
    ::= { f3AccFlowPointCpdV2Entry 24 }

f3AccFlowPointCpdV2Mac00DispType OBJECT-TYPE
    SYNTAX      CmControlProtocolDispType 
    MAX-ACCESS  read-write
    STATUS      current
    DESCRIPTION
       "MAC Address 01:80:C2:00:00:00 Disposition type."
    ::= { f3AccFlowPointCpdV2Entry 25 }

f3AccFlowPointCpdV2Mac01DispType OBJECT-TYPE
    SYNTAX      CmControlProtocolDispType 
    MAX-ACCESS  read-write
    STATUS      current
    DESCRIPTION
       "MAC Address 01:80:C2:00:00:01 Disposition type."
    ::= { f3AccFlowPointCpdV2Entry 26 }

f3AccFlowPointCpdV2Mac02DispType OBJECT-TYPE
    SYNTAX      CmControlProtocolDispType 
    MAX-ACCESS  read-write
    STATUS      current
    DESCRIPTION
       "MAC Address 01:80:C2:00:00:02 Disposition type."
    ::= { f3AccFlowPointCpdV2Entry 27 }

f3AccFlowPointCpdV2Mac03DispType OBJECT-TYPE
    SYNTAX      CmControlProtocolDispType 
    MAX-ACCESS  read-write
    STATUS      current
    DESCRIPTION
       "MAC Address 01:80:C2:00:00:03 Disposition type."
    ::= { f3AccFlowPointCpdV2Entry 28 }

f3AccFlowPointCpdV2Mac04DispType OBJECT-TYPE
    SYNTAX      CmControlProtocolDispType 
    MAX-ACCESS  read-write
    STATUS      current
    DESCRIPTION
       "MAC Address 01:80:C2:00:00:04 Disposition type."
    ::= { f3AccFlowPointCpdV2Entry 29 }

f3AccFlowPointCpdV2Mac05DispType OBJECT-TYPE
    SYNTAX      CmControlProtocolDispType 
    MAX-ACCESS  read-write
    STATUS      current
    DESCRIPTION
       "MAC Address 01:80:C2:00:00:05 Disposition type."
    ::= { f3AccFlowPointCpdV2Entry 30 }

f3AccFlowPointCpdV2Mac06DispType OBJECT-TYPE
    SYNTAX      CmControlProtocolDispType 
    MAX-ACCESS  read-write
    STATUS      current
    DESCRIPTION
       "MAC Address 01:80:C2:00:00:06 Disposition type."
    ::= { f3AccFlowPointCpdV2Entry 31 }

f3AccFlowPointCpdV2Mac07DispType OBJECT-TYPE
    SYNTAX      CmControlProtocolDispType 
    MAX-ACCESS  read-write
    STATUS      current
    DESCRIPTION
       "MAC Address 01:80:C2:00:00:07 Disposition type."
    ::= { f3AccFlowPointCpdV2Entry 32 }

f3AccFlowPointCpdV2Mac08DispType OBJECT-TYPE
    SYNTAX      CmControlProtocolDispType 
    MAX-ACCESS  read-write
    STATUS      current
    DESCRIPTION
       "MAC Address 01:80:C2:00:00:08 Disposition type."
    ::= { f3AccFlowPointCpdV2Entry 33 }

f3AccFlowPointCpdV2Mac09DispType OBJECT-TYPE
    SYNTAX      CmControlProtocolDispType 
    MAX-ACCESS  read-write
    STATUS      current
    DESCRIPTION
       "MAC Address 01:80:C2:00:00:09 Disposition type."
    ::= { f3AccFlowPointCpdV2Entry 34 }

f3AccFlowPointCpdV2Mac0ADispType OBJECT-TYPE
    SYNTAX      CmControlProtocolDispType 
    MAX-ACCESS  read-write
    STATUS      current
    DESCRIPTION
       "MAC Address 01:80:C2:00:00:0A Disposition type."
    ::= { f3AccFlowPointCpdV2Entry 35 }

f3AccFlowPointCpdV2Mac0BDispType OBJECT-TYPE
    SYNTAX      CmControlProtocolDispType 
    MAX-ACCESS  read-write
    STATUS      current
    DESCRIPTION
       "MAC Address 01:80:C2:00:00:0B Disposition type."
    ::= { f3AccFlowPointCpdV2Entry 36 }

f3AccFlowPointCpdV2Mac0CDispType OBJECT-TYPE
    SYNTAX      CmControlProtocolDispType 
    MAX-ACCESS  read-write
    STATUS      current
    DESCRIPTION
       "MAC Address 01:80:C2:00:00:0C Disposition type."
    ::= { f3AccFlowPointCpdV2Entry 37 }

f3AccFlowPointCpdV2Mac0DDispType OBJECT-TYPE
    SYNTAX      CmControlProtocolDispType 
    MAX-ACCESS  read-write
    STATUS      current
    DESCRIPTION
       "MAC Address 01:80:C2:00:00:0D Disposition type."
    ::= { f3AccFlowPointCpdV2Entry 38 }

f3AccFlowPointCpdV2Mac0EDispType OBJECT-TYPE
    SYNTAX      CmControlProtocolDispType 
    MAX-ACCESS  read-write
    STATUS      current
    DESCRIPTION
       "MAC Address 01:80:C2:00:00:0E Disposition type."
    ::= { f3AccFlowPointCpdV2Entry 39 }

f3AccFlowPointCpdV2Mac0FDispType OBJECT-TYPE
    SYNTAX      CmControlProtocolDispType 
    MAX-ACCESS  read-write
    STATUS      current
    DESCRIPTION
       "MAC Address 01:80:C2:00:00:0F Disposition type."
    ::= { f3AccFlowPointCpdV2Entry 40 }

f3AccFlowPointCpdV2NearestLLDPDispType OBJECT-TYPE
    SYNTAX      CmControlProtocolDispType 
    MAX-ACCESS  read-write
    STATUS      current
    DESCRIPTION
       "LLDP (Link Layer Discovery Protocol) Nearest Bridge Disposition type."
    ::= { f3AccFlowPointCpdV2Entry 41 }

f3AccFlowPointCpdV2NonTpmrLLDPDispType OBJECT-TYPE
    SYNTAX      CmControlProtocolDispType 
    MAX-ACCESS  read-write
    STATUS      current
    DESCRIPTION
       "LLDP (Link Layer Discovery Protocol) Non-TPMR Bridge Disposition type."
    ::= { f3AccFlowPointCpdV2Entry 42 }

f3AccFlowPointCpdV2CustomerLLDPDispType OBJECT-TYPE
    SYNTAX      CmControlProtocolDispType 
    MAX-ACCESS  read-write
    STATUS      current
    DESCRIPTION
       "LLDP (Link Layer Discovery Protocol) Customer Bridge Disposition type."
    ::= { f3AccFlowPointCpdV2Entry 43 }

--
--  Access Flowpoint table extension for Learning Control configuration
--
f3AccFlowPointLearningConfigTable  OBJECT-TYPE
    SYNTAX      SEQUENCE OF F3AccFlowPointLearningConfigEntry   
    MAX-ACCESS  not-accessible
    STATUS      current
    DESCRIPTION
            "This table extends f3AccFlowPointTable to provide parameters for MAC Table control
             configuration."
    ::= { f3FpmConfigObjects 6 }

f3AccFlowPointLearningConfigEntry  OBJECT-TYPE
    SYNTAX      F3AccFlowPointLearningConfigEntry   
    MAX-ACCESS  not-accessible
    STATUS      current
    DESCRIPTION
            "A conceptual row in the f3AccFlowPointLearningConfigTable."
    AUGMENTS { f3AccFlowPointEntry }
    ::= { f3AccFlowPointLearningConfigTable 1 }

F3AccFlowPointLearningConfigEntry ::= SEQUENCE {
    f3AccFlowPointLearningConfigLearningEnabled       TruthValue,
    f3AccFlowPointLearningConfigMaxFwdEntries         Integer32,
    f3AccFlowPointLearningConfigProtectLearningCtrl   ProtectLearningControl,
    f3AccFlowPointLearningConfigAction                FlowLearningConfigAction
}

f3AccFlowPointLearningConfigLearningEnabled OBJECT-TYPE
    SYNTAX        TruthValue
    MAX-ACCESS    read-write
    STATUS        current
    DESCRIPTION
         "This object allows configuring Learning Control on this Flowpoint."
    ::= { f3AccFlowPointLearningConfigEntry 1 }

f3AccFlowPointLearningConfigMaxFwdEntries OBJECT-TYPE
    SYNTAX        Integer32
    MAX-ACCESS    read-write
    STATUS        current
    DESCRIPTION
         "This object allows configuring the maximum number of Forwarding Entries 
          on this Flowpoint."
    ::= { f3AccFlowPointLearningConfigEntry 2 }

f3AccFlowPointLearningConfigProtectLearningCtrl OBJECT-TYPE
    SYNTAX        ProtectLearningControl
    MAX-ACCESS    read-write
    STATUS        current
    DESCRIPTION
         "This object allows configuring Learning Control on this Flowpoint."
    ::= { f3AccFlowPointLearningConfigEntry 3 }

f3AccFlowPointLearningConfigAction OBJECT-TYPE
    SYNTAX        FlowLearningConfigAction
    MAX-ACCESS    read-write
    STATUS        current
    DESCRIPTION
         "This objects allows performing user action on Flow Learning Table."
    ::= { f3AccFlowPointLearningConfigEntry 4 }

--
--  Network Flow Point Table
--

f3NetFlowPointTable OBJECT-TYPE
    SYNTAX      SEQUENCE OF F3NetFlowPointEntry
    MAX-ACCESS  not-accessible
    STATUS      current
    DESCRIPTION
            "A list of entries corresponding to Network Flow Point
             for configuration purposes."
    ::= { f3FpmConfigObjects 7 }

f3NetFlowPointEntry OBJECT-TYPE
    SYNTAX      F3NetFlowPointEntry 
    MAX-ACCESS  not-accessible
    STATUS      current
    DESCRIPTION
            "A conceptual row in the f3NetFlowPointTable.
             These entries represent an Network Flow Point.
             If the Flow Point attached to a lag, the slotIndex should 
             be 255 (255 is used to identify the Flow Point belongs to lag), 
             and the cmEthernetNetPortIndex should be the f3LagIndex."
             
    INDEX { neIndex, shelfIndex, slotIndex, cmEthernetNetPortIndex, f3NetFlowPointIndex }
    ::= { f3NetFlowPointTable 1 }

F3NetFlowPointEntry ::= SEQUENCE {
    f3NetFlowPointIndex                           Integer32,
    f3NetFlowPointAlias                           DisplayString,

    f3NetFlowPointAdminState                      AdminState,
    f3NetFlowPointOperationalState                OperationalState,
    f3NetFlowPointSecondaryState                  SecondaryState,

    f3NetFlowPointAssociatedFlowId                VariablePointer,

    f3NetFlowPointIngressMultiCOSEnabled          TruthValue,
    f3NetFlowPointIngressCOS                      Integer32,
    f3NetFlowPointEgressShapingType               ShapingType,

    f3NetFlowPointIngressVlanMemberList           DisplayString,
    f3NetFlowPointVlanMemberAction                FlowVlanActionType,
    f3NetFlowPointVlanMemberActionVlan            DisplayString,
    f3NetFlowPointIngressUntaggedFrameEnabled     TruthValue,

    f3NetFlowPointCTagControl                     FlowTagControl,
    f3NetFlowPointCTagVlanId                      VlanId,
    f3NetFlowPointCTagVlanPriority                VlanPriority,
    f3NetFlowPointSTagControl                     FlowTagControl,
    f3NetFlowPointSTagVlanId                      VlanId,
    f3NetFlowPointSTagVlanPriority                VlanPriority,
        
    f3NetFlowPointEgressOuterTagPrioMapEnabled    TruthValue,
    f3NetFlowPointEgressInnerTagPrioMapEnabled    TruthValue,
    f3NetFlowPointSESFramesLossThresholdRatio     Integer32,
    f3NetFlowPointDefaultMemberEnabled            TruthValue,
    
    f3NetFlowPointMcastRateLimitEnabled           TruthValue,
    f3NetFlowPointMcastRateLimitSpeedLo           Unsigned32,
    f3NetFlowPointMcastRateLimitSpeedHi           Unsigned32,
    f3NetFlowPointBcastRateLimitEnabled           TruthValue,
    f3NetFlowPointBcastRateLimitSpeedLo           Unsigned32,
    f3NetFlowPointBcastRateLimitSpeedHi           Unsigned32,
    f3NetFlowPointCombinedRateLimitEnabled        TruthValue,
    f3NetFlowPointCombinedRateLimitSpeedLo        Unsigned32,
    f3NetFlowPointCombinedRateLimitSpeedHi        Unsigned32,

    f3NetFlowPointSplitHorizonGroupOID            VariablePointer,
    f3NetFlowPointLoopAvoidance                   VariablePointer,
    f3NetFlowPointHierarchicalCOSEnabled          TruthValue,
    f3NetFlowPointMaximumBWLo                     Unsigned32,
    f3NetFlowPointMaximumBWHi                     Unsigned32,
    f3NetFlowPointGuaranteedBWLo                  Unsigned32,
    f3NetFlowPointGuaranteedBWHi                  Unsigned32,
    f3NetFlowPointAutoBandwidthConfigEnabled      TruthValue,
    f3NetFlowPointAutoCIRPercentage               Integer32,
    f3NetFlowPointFrameFwdEnabled                 TruthValue,

    f3NetFlowPointStorageType                     StorageType,
    f3NetFlowPointRowStatus                       RowStatus,

    f3NetFlowPointUsePortPrioMapProfile           TruthValue,
    f3NetFlowPointRefPrioMapProfile               VariablePointer,
    f3NetFlowpointRefConnectGuardFlowObject       VariablePointer,
    f3NetFlowpointSecureBlockingControl           TruthValue,
    f3NetFlowpointSecureState                     FlowSecState,

    f3NetFlowPointElmiEvcIdentifier               DisplayString
}

f3NetFlowPointIndex OBJECT-TYPE
    SYNTAX      Integer32 (1..65535)
    MAX-ACCESS  not-accessible
    STATUS      current
    DESCRIPTION
       "The integer index value corresponding to an Flow Point." 
    ::= { f3NetFlowPointEntry 1 }

f3NetFlowPointAlias OBJECT-TYPE
    SYNTAX      DisplayString (SIZE(0..64))
    MAX-ACCESS  read-create
    STATUS      current
    DESCRIPTION
       "This object allows SNMP management entities to provide a
        circuit identifier with the Flow Point."
    ::= { f3NetFlowPointEntry 2 }

f3NetFlowPointAdminState OBJECT-TYPE
    SYNTAX      AdminState 
    MAX-ACCESS  read-create
    STATUS      current
    DESCRIPTION
       "This object represents the Administrative State of the Flow Point." 
    ::= { f3NetFlowPointEntry 3 }

f3NetFlowPointOperationalState OBJECT-TYPE
    SYNTAX      OperationalState 
    MAX-ACCESS  read-only
    STATUS      current
    DESCRIPTION
       "This object represents the Operational State of the Flow Point." 
    ::= { f3NetFlowPointEntry 4 }

f3NetFlowPointSecondaryState OBJECT-TYPE
    SYNTAX      SecondaryState 
    MAX-ACCESS  read-only
    STATUS      current
    DESCRIPTION
       "This object represents the Secondary State of the Flow Point." 
    ::= { f3NetFlowPointEntry 5 }

f3NetFlowPointAssociatedFlowId OBJECT-TYPE
    SYNTAX      VariablePointer
    MAX-ACCESS  read-only
    STATUS      current
    DESCRIPTION
       "This object provides the association of an Flow with an Flow Point."
    ::= { f3NetFlowPointEntry 6 }

f3NetFlowPointIngressMultiCOSEnabled OBJECT-TYPE
    SYNTAX     TruthValue
    MAX-ACCESS read-create
    STATUS     current
    DESCRIPTION
       "This object allows specification of ingress multiple COS
       (Class of Service) Flow Point." 
    ::= { f3NetFlowPointEntry 7 }

f3NetFlowPointIngressCOS OBJECT-TYPE
    SYNTAX     Integer32
    MAX-ACCESS read-create
    STATUS     deprecated
    DESCRIPTION
       "This object allows specification of ingress COS 
       (Class of Service) Flow Point.

       This attribute has been deprecated and is not supported. The
       Ingress COS is determined from the flowpoint's associated
       Priority Mapping Profle."
    ::= { f3NetFlowPointEntry 8 }
     
f3NetFlowPointEgressShapingType OBJECT-TYPE
    SYNTAX     ShapingType
    MAX-ACCESS read-write
    STATUS     current
    DESCRIPTION
       "This object allows specification of Shaping Type for Flow Point.
        For 8.1.1 release, only flow-based Shaping Type is supported." 
    ::= { f3NetFlowPointEntry 9 }

f3NetFlowPointIngressVlanMemberList OBJECT-TYPE
    SYNTAX     DisplayString (SIZE (0..512))
    MAX-ACCESS read-create
    STATUS     current
    DESCRIPTION
       "It allows specification of VLAN members of the Flow Point.
        VLAN members are comma separated, of the form X-Y where X is the
        VLAN Id and Y is the VLAN Priority. VLAN members can be of
        the form X-* or X (vlan X with all priorities), *-Y (all vlans
        with priority Y), and X1:X2 (range of vlans from X1 to X2, 
        all priorities). Members with specific VLAN Id and specific
        VLAN Priority are not supported. Once the Flow Point is created,
        this attribute can only be updated using f3NetFlowPointVlanMemberAction
        and f3NetFlowPointVlanMemberActionVlan objects."
    ::= { f3NetFlowPointEntry 10 }

f3NetFlowPointVlanMemberAction OBJECT-TYPE
    SYNTAX     FlowVlanActionType 
    MAX-ACCESS read-write
    STATUS     current
    DESCRIPTION
       "This object allows to add or remove the VLAN members specified by
        f3NetFlowPointVlanMemberActionVlan object. SNMP manager must first
        configure the VLAN member to be added/removed in the object
        f3NetFlowPointVlanMemberActionVlan and then should specify
        f3NetFlowPointVlanMemberAction on whether to add/remove the specified
        VLAN member."
    ::= { f3NetFlowPointEntry 11 }

f3NetFlowPointVlanMemberActionVlan OBJECT-TYPE
    SYNTAX     DisplayString (SIZE (0..16))
    MAX-ACCESS read-create
    STATUS     current
    DESCRIPTION
       "This object allows adding/removing VLAN members to a Flow Point.
        VLAN member is of the form X-Y where X is the VLAN Id and Y is
        the VLAN Priority. VLAN members can be of the form X-* (vlan X 
        with all priorities), *-Y (all vlans with priority Y), and X1:X2 
        (range of vlans from X1 to X2, all priorities). Members with 
        specific VLAN Id and specific VLAN Priority are not supported.
        In order to add/remove VLAN member to a flow, user must specify
        this object with appropriate VLAN and then 
        invoke f3NetFlowPointVlanMemberAction."
    ::= { f3NetFlowPointEntry 12 }
     
f3NetFlowPointIngressUntaggedFrameEnabled OBJECT-TYPE
    SYNTAX     TruthValue 
    MAX-ACCESS read-create
    STATUS     current
    DESCRIPTION
       "This object allows to specify whether or not the Flow Point
        supports untagged frame."
    ::= { f3NetFlowPointEntry 13 }

f3NetFlowPointCTagControl OBJECT-TYPE
    SYNTAX     FlowTagControl
    MAX-ACCESS read-create
    STATUS     current
    DESCRIPTION
       "This object allows specification of the tag management 
        operation on the C-TAG.  Supported types are 'push', 'pushvid',
        'swaptag', 'swapvid' and 'none'. If the type is 'push',
        the VLAN Id (f3NetFlowPointCTagVlanId) and priority
        (f3NetFlowPointCTagVlanPriority) are pushed onto the frame;
        if the type is 'pushvid', only the VLAN Id (12 bits) is pushed,
        the Priority is copied from incoming tag's priority;
        if the type is 'swaptag', both VLAN Id and Priority (15 bits)
        are swapped with the specified f3NetFlowPointCTagVlanId and 
        f3NetFlowPointCTagVlanPriority;
        if the type is 'swapvid', only the VLAN Id (12 bits) are 
        swapped with the specified f3NetFlowPointCTagVlanId; 
        if the type is 'none', no C-TAG management is performed."
    ::= { f3NetFlowPointEntry 14 }

f3NetFlowPointCTagVlanId OBJECT-TYPE
    SYNTAX     VlanId
    MAX-ACCESS read-create
    STATUS     current
    DESCRIPTION
       "This object allows specification of the VLAN Id to
        be pushed or swapped, based on the value of 
        f3NetFlowPointIngressCTagControl. It is applicable 
        for 'push', 'swaptag', 'swapvid' and 'pushvid' control types."
    ::= { f3NetFlowPointEntry 15 }

f3NetFlowPointCTagVlanPriority OBJECT-TYPE
    SYNTAX     VlanPriority
    MAX-ACCESS read-create
    STATUS     current
    DESCRIPTION
       "This object allows specification of the VLAN Priority to
        be pushed or swapped, based on the value of f3NetFlowPointIngressCTagControl.
        It is applicable for 'push' and 'swaptag' control types."
    ::= { f3NetFlowPointEntry 16 }
     
f3NetFlowPointSTagControl OBJECT-TYPE
    SYNTAX     FlowTagControl
    MAX-ACCESS read-create
    STATUS     current
    DESCRIPTION
       "This object allows specification of the tag management 
        operation on the S-TAG.  Supported types are 'push', 'pushvid',
        'swaptag', 'swapvid' and 'none'. If the type is 'push', 
        the VLAN Id (f3NetFlowPointSTagVlanId) and priority
        (f3NetFlowPointSTagVlanPriority) are pushed onto the frame;
        if the type is 'pushvid', only the VLAN Id (12 bits) is pushed,
        the Priority is copied from incoming tag's priority;
        if the type is 'swaptag', both VLAN Id and Priority (15 bits) 
        are swapped with the specified f3NetFlowPointSTagVlanId and 
        f3NetFlowPointSTagVlanPriority;
        if the type is 'swapvid', only the VLAN Id (12 bits) are 
        swapped with the specified f3NetFlowPointSTagVlanId; 
        if the type is 'none', no S-TAG management is performed."
    ::= { f3NetFlowPointEntry 17 }

f3NetFlowPointSTagVlanId OBJECT-TYPE
    SYNTAX     VlanId
    MAX-ACCESS read-create
    STATUS     current
    DESCRIPTION
       "This object allows specification of the VLAN Id to
        be pushed or swapped, based on the value of 
        f3NetFlowPointIngressSTagControl. It is applicable 
        for 'push', 'swaptag', 'swapvid' and 'pushvid' control types."
    ::= { f3NetFlowPointEntry 18 }

f3NetFlowPointSTagVlanPriority OBJECT-TYPE
    SYNTAX     VlanPriority
    MAX-ACCESS read-create
    STATUS     current
    DESCRIPTION
       "This object allows specification of the VLAN Priority to
        be pushed or swapped, based on the value of 
        f3NetFlowPointIngressSTagControl. It is applicable
        for 'push' and 'swaptag' control types."
    ::= { f3NetFlowPointEntry 19 }
     
f3NetFlowPointEgressOuterTagPrioMapEnabled OBJECT-TYPE
    SYNTAX     TruthValue
    MAX-ACCESS read-create
    STATUS     current
    DESCRIPTION
       "This object defines whether to use the Egress Prio 
        Mapping to swap the priority of outer tag. When Enabled,
        it indicates that the operation specified in the 
        EgressPrioMapTable would be applied to Flow for specified COS.
        When Disabled,the EgressPrioMapTable operations are ignored 
        for specified Flow COS."
    ::= { f3NetFlowPointEntry 20 }

f3NetFlowPointEgressInnerTagPrioMapEnabled OBJECT-TYPE
    SYNTAX     TruthValue
    MAX-ACCESS read-create
    STATUS     current
    DESCRIPTION
       "This object defines whether to use the Egress Prio
        Mapping to swap the priority of inner tag. When Enabled,
        it indicates that the operation specified in the 
        EgressPrioMapTable would be applied to Flow for specified COS.
        When Disabled, the EgressPrioMapTable operations are ignored
        for specified Flow COS."
    ::= { f3NetFlowPointEntry 21 }

f3NetFlowPointSESFramesLossThresholdRatio OBJECT-TYPE 
    SYNTAX     Integer32 (0..100)
    MAX-ACCESS read-create
    STATUS     current
    DESCRIPTION
       "This object is used to specify the frame-loss ratio 
        per flow that starts counting Severely Errored Seconds (SES) 
        on the flowpoint.
        This functionality is applicable if the flowpoint is monitored
        using the Y.1731 ESA functionality." 
    ::= { f3NetFlowPointEntry 22 }

f3NetFlowPointDefaultMemberEnabled OBJECT-TYPE
    SYNTAX      TruthValue
    MAX-ACCESS  read-create
    STATUS      current
    DESCRIPTION
       "Truth Value means that on this FP, the membership is all the tag
        packets without match any other membership associated to the port.
        Untagged means untagged flow. Default only care tagged flow."
    ::= { f3NetFlowPointEntry 23 }

f3NetFlowPointMcastRateLimitEnabled OBJECT-TYPE
    SYNTAX      TruthValue
    MAX-ACCESS  read-create
    STATUS      current
    DESCRIPTION
       "Whether multicast packets need be limited per FP." 
    ::= { f3NetFlowPointEntry 24 }

f3NetFlowPointMcastRateLimitSpeedLo OBJECT-TYPE
    SYNTAX      Unsigned32
    MAX-ACCESS  read-create
    STATUS      current
    DESCRIPTION
       "The rate limiting for multicast packets per FP. When
        f3NetFlowPointMcastRateLimitEnabled and the value is 0,
        it means all multicast frame are dropped. This objects
        only represents low 32 bits."
    ::= { f3NetFlowPointEntry 25 }

f3NetFlowPointMcastRateLimitSpeedHi OBJECT-TYPE
    SYNTAX      Unsigned32
    MAX-ACCESS  read-create
    STATUS      current
    DESCRIPTION
       "The rate limiting for multicast packets per FP. When
        f3NetFlowPointMcastRateLimitEnabled and the value is 0, 
        it means all multicast frame are dropped. This objects
        only represents high 32 bits." 
    ::= { f3NetFlowPointEntry 26 }

f3NetFlowPointBcastRateLimitEnabled OBJECT-TYPE
    SYNTAX      TruthValue
    MAX-ACCESS  read-create
    STATUS      current
    DESCRIPTION
       "Whether broadcast packets need be limited per FP." 
    ::= { f3NetFlowPointEntry 27 }

f3NetFlowPointBcastRateLimitSpeedLo OBJECT-TYPE
    SYNTAX      Unsigned32
    MAX-ACCESS  read-create
    STATUS      current
    DESCRIPTION
       "The rate limiting for broadcast packets per FP. When
        f3NetFlowPointBcastRateLimitEnabled and the value is 0, 
        it means all multicast frame are dropped. This objects
        only represents low 32 bits." 
    ::= { f3NetFlowPointEntry 28 }

f3NetFlowPointBcastRateLimitSpeedHi OBJECT-TYPE
    SYNTAX      Unsigned32
    MAX-ACCESS  read-create
    STATUS      current
    DESCRIPTION
       "The rate limiting for broadcast packets per FP. When 
        f3NetFlowPointBcastRateLimitEnabled and the value is 0, 
        it means all multicast frame are dropped. This objects
        only represents high 32 bits."
    ::= { f3NetFlowPointEntry 29 }

f3NetFlowPointCombinedRateLimitEnabled OBJECT-TYPE
    SYNTAX      TruthValue
    MAX-ACCESS  read-create
    STATUS      current
    DESCRIPTION
       "Whether broadcast and multicast packets need be limited per FP." 
    ::= { f3NetFlowPointEntry 30 }

f3NetFlowPointCombinedRateLimitSpeedLo OBJECT-TYPE
    SYNTAX      Unsigned32
    MAX-ACCESS  read-create
    STATUS      current
    DESCRIPTION
       "The rate limiting for broadcast and multicast packets per FP.
        When f3NetFlowPointCombinedRateLimitEnabled is true and the value is 0, 
        it means all broadcast and multicast frame are dropped. This object
        only represents low 32 bits." 
    ::= { f3NetFlowPointEntry 31 }

f3NetFlowPointCombinedRateLimitSpeedHi OBJECT-TYPE
    SYNTAX      Unsigned32
    MAX-ACCESS  read-create
    STATUS      current
    DESCRIPTION
       "The rate limiting for broadcast and multicast packets per FP.
        When f3NetFlowPointCombinedRateLimitEnabled is true and the value is 0, 
        it means all broadcast and multicast frame are dropped. This object
        only represents high 32 bits." 
    ::= { f3NetFlowPointEntry 32 }

f3NetFlowPointSplitHorizonGroupOID OBJECT-TYPE
    SYNTAX      VariablePointer
    MAX-ACCESS  read-create
    STATUS      current
    DESCRIPTION
       "Specifies the Split-Horizon Group OID. If there is no SHG, the value is none." 
    ::= { f3NetFlowPointEntry 33 }

f3NetFlowPointLoopAvoidance OBJECT-TYPE
    SYNTAX      VariablePointer
    MAX-ACCESS  read-create
    STATUS      current
    DESCRIPTION
       "EID of this associated Loop Avoidance protocol entity.
        A value of NONE indicates there is no loop avoidance protocol.
        Currently ERP EID is filled when ELAN service is created." 
    ::= { f3NetFlowPointEntry 34 }

f3NetFlowPointHierarchicalCOSEnabled OBJECT-TYPE
    SYNTAX      TruthValue
    MAX-ACCESS  read-create
    STATUS      current
    DESCRIPTION
       "Enable or Disable Hierarchical COS shaping (flow shaping)." 
    ::= { f3NetFlowPointEntry 35 }

f3NetFlowPointMaximumBWLo OBJECT-TYPE
    SYNTAX      Unsigned32
    MAX-ACCESS  read-create
    STATUS      current
    DESCRIPTION
       "This attribute description the Flow Point maximum bandwidth.
        This object only represents low 32 bits." 
    ::= { f3NetFlowPointEntry 36 }

f3NetFlowPointMaximumBWHi OBJECT-TYPE
    SYNTAX      Unsigned32
    MAX-ACCESS  read-create
    STATUS      current
    DESCRIPTION
       "This attribute description the Flow Point maximum bandwidth.
        This object only represents high 32 bits." 
    ::= { f3NetFlowPointEntry 37 }

f3NetFlowPointGuaranteedBWLo OBJECT-TYPE
    SYNTAX      Unsigned32
    MAX-ACCESS  read-create
    STATUS      current
    DESCRIPTION
       "This attribute description the Flow Point guaranteed bandwidth.
        This object only represents low 32 bits." 
    ::= { f3NetFlowPointEntry 38 }

f3NetFlowPointGuaranteedBWHi OBJECT-TYPE
    SYNTAX      Unsigned32
    MAX-ACCESS  read-create
    STATUS      current
    DESCRIPTION
       "This attribute description the Flow Point guaranteed bandwidth.
        This objects only represents high 32 bits." 
    ::= { f3NetFlowPointEntry 39 }
    
f3NetFlowPointAutoBandwidthConfigEnabled OBJECT-TYPE
    SYNTAX      TruthValue
    MAX-ACCESS  read-create
    STATUS      current
    DESCRIPTION
       "This object specifies the shaper bandwidth is automatically adjusted 
        by the system. For a single COS Flow Point, the shaper EIR bandwidth is 
        set to the maximum port bandwidth; the shaper CIR is set to the available 
        port bandwidth multiplied by the value of the f3NetFlowPointAutoCIRPercentage
        object. For a Hierarchical-COS Flow Point, the f3NetFlowPointMaximumBWLo and
        f3NetFlowPointMaximumBWHi are set to the maximum port bandwidth; 
        the f3NetFlowPointGuaranteedBWLo and f3NetFlowPointGuaranteedBWHi are set to 
        the available port bandwidth multiplied by the value of the 
        f3NetFlowPointAutoCIRPercentage object. The value of this object must be FALSE 
        when f3NetFlowPointIngressMultiCOSEnabled is TRUE and 
        f3NetFlowPointHierarchicalCOSEnabled is FALSE." 
    ::= { f3NetFlowPointEntry 40 }
    
f3NetFlowPointAutoCIRPercentage OBJECT-TYPE
    SYNTAX      Integer32 (0..100)
    MAX-ACCESS  read-create
    STATUS      current
    DESCRIPTION
       "This object specifies the percentage of available shaper CIR to be assigned 
        to this Flow Point when f3NetFlowPointAutoBandwidthConfigEnabled is TRUE." 
    ::= { f3NetFlowPointEntry 41 }

f3NetFlowPointFrameFwdEnabled OBJECT-TYPE
    SYNTAX      TruthValue
    MAX-ACCESS  read-create
    STATUS      current
    DESCRIPTION
       "When enabled Flow Point will forward frames it receives. 
        When disabled, the Flow Point will not forward frames it receives." 
    ::= { f3NetFlowPointEntry 42 }

f3NetFlowPointStorageType OBJECT-TYPE
    SYNTAX     StorageType
    MAX-ACCESS read-create
    STATUS     current
    DESCRIPTION
       "The type of storage configured for this entry."
    ::= { f3NetFlowPointEntry 43 }

f3NetFlowPointRowStatus OBJECT-TYPE
    SYNTAX      RowStatus
    MAX-ACCESS  read-create
    STATUS      current
    DESCRIPTION
       "The status of this row.
        An entry MUST NOT exist in the active state unless all
        objects in the entry have an appropriate value, as described
        in the description clause for each writable object.

        The values of f3NetFlowPointRowStatus supported are
        createAndGo(4) and destroy(6).  All mandatory attributes
        must be specified in a single SNMP SET request with
        f3NetFlowPointRowStatus value as createAndGo(4).
        Upon successful row creation, this object has a
        value of active(1).

        The f3NetFlowPointRowStatus object may be modified if
        the associated instance of this object is equal to active(1)."
    ::= { f3NetFlowPointEntry 44 }

f3NetFlowPointUsePortPrioMapProfile OBJECT-TYPE
    SYNTAX      TruthValue  
    MAX-ACCESS  read-write
    STATUS      current
    DESCRIPTION
         "This indicates whether the flow point is using, if true, the port's 
         Priority Mapping Profile or, if false, is using its own
         Priority Mapping Profile."
    ::= { f3NetFlowPointEntry 45 }

f3NetFlowPointRefPrioMapProfile OBJECT-TYPE
    SYNTAX      VariablePointer  
    MAX-ACCESS  read-write
    STATUS      current
    DESCRIPTION
         "This object allows to set priority map profile."
    ::= { f3NetFlowPointEntry 46 }

f3NetFlowpointRefConnectGuardFlowObject OBJECT-TYPE
    SYNTAX     VariablePointer
    MAX-ACCESS read-write
    STATUS     current
    DESCRIPTION
          "This object specifies Mac Sec flow object OID."
     ::= { f3NetFlowPointEntry 47 }

f3NetFlowpointSecureBlockingControl OBJECT-TYPE
    SYNTAX     TruthValue
    MAX-ACCESS read-write
    STATUS     current
    DESCRIPTION
          "This object can be used to enable/disable secure block."
     ::= { f3NetFlowPointEntry 48 }

f3NetFlowpointSecureState OBJECT-TYPE
    SYNTAX     FlowSecState
    MAX-ACCESS read-only
    STATUS     current
    DESCRIPTION
          "This object specifies the secure state of this flow."
     ::= { f3NetFlowPointEntry 49 }

f3NetFlowPointElmiEvcIdentifier OBJECT-TYPE
    SYNTAX      DisplayString  
    MAX-ACCESS  read-create
    STATUS      current
    DESCRIPTION
         "This object specifies Network FlowPoint Evc Identifier 
          required for E-LMI feature."
    ::= { f3NetFlowPointEntry 50 }

--
--  Net Flow Point QoS Shaper
--

f3NetFpQosShaperTable OBJECT-TYPE
    SYNTAX      SEQUENCE OF F3NetFpQosShaperEntry
    MAX-ACCESS  not-accessible
    STATUS      current
    DESCRIPTION
       "A list of entries corresponding to Net Flow Point 
        Quality of Service Shaper for configuration purposes."
    ::= { f3FpmConfigObjects 8 }

f3NetFpQosShaperEntry OBJECT-TYPE
    SYNTAX      F3NetFpQosShaperEntry 
    MAX-ACCESS  not-accessible
    STATUS      current
    DESCRIPTION
       "A conceptual row in the f3NetFpQosShaperTable. 
        These entries represent an Net Flow Point Quality 
        of Service Shaper."
    INDEX { neIndex, shelfIndex, slotIndex, cmEthernetNetPortIndex, 
            f3NetFlowPointIndex, f3NetFpQosShaperIndex }
    ::= { f3NetFpQosShaperTable 1 }

F3NetFpQosShaperEntry ::= SEQUENCE {
    f3NetFpQosShaperIndex               Integer32,

    f3NetFpQosShaperAdminState          AdminState,
    f3NetFpQosShaperOperationalState    OperationalState,
    f3NetFpQosShaperSecondaryState      SecondaryState,

    f3NetFpQosShaperCIRLo               Unsigned32,
    f3NetFpQosShaperCIRHi               Unsigned32,
    f3NetFpQosShaperEIRLo               Unsigned32,
    f3NetFpQosShaperEIRHi               Unsigned32,
    f3NetFpQosShaperCBS                 Unsigned32,
    f3NetFpQosShaperEBS                 Unsigned32,
    f3NetFpQosShaperBufferSize          Unsigned32,
    f3NetFpQosShaperCOS                 Integer32,
    
    f3NetFpQosShaperStorageType         StorageType,
    f3NetFpQosShaperRowStatus           RowStatus
}

f3NetFpQosShaperIndex OBJECT-TYPE
    SYNTAX      Integer32 (1..8)
    MAX-ACCESS  not-accessible
    STATUS      current
    DESCRIPTION
       "The unique integer index value corresponding to a Quality 
        of Service Shaper."
    ::= { f3NetFpQosShaperEntry 1 }

f3NetFpQosShaperAdminState OBJECT-TYPE
    SYNTAX      AdminState 
    MAX-ACCESS  read-create
    STATUS      current
    DESCRIPTION
       "This object represents the Administrative State of a Shaper." 
    ::= { f3NetFpQosShaperEntry 2 }

f3NetFpQosShaperOperationalState OBJECT-TYPE
    SYNTAX      OperationalState 
    MAX-ACCESS  read-only
    STATUS      current
    DESCRIPTION
       "This object represents the Operational State of a Shaper." 
    ::= { f3NetFpQosShaperEntry 3 }

f3NetFpQosShaperSecondaryState OBJECT-TYPE
    SYNTAX      SecondaryState 
    MAX-ACCESS  read-only
    STATUS      current
    DESCRIPTION
       "This object represents the Secondary State of the Shaper." 
    ::= { f3NetFpQosShaperEntry 4 }

f3NetFpQosShaperCIRLo OBJECT-TYPE
    SYNTAX      Unsigned32
    MAX-ACCESS  read-create
    STATUS      current
    DESCRIPTION
       "This object represents the Commited Information Rate (CIR)
        (Lower 32 bits) of the Shaper."
    ::= { f3NetFpQosShaperEntry 5 }
     
f3NetFpQosShaperCIRHi OBJECT-TYPE
    SYNTAX      Unsigned32
    MAX-ACCESS  read-create
    STATUS      current
    DESCRIPTION
       "This object represents the Commited Information Rate (CIR)
        (Higher 32 bits) of the Shaper."
    ::= { f3NetFpQosShaperEntry 6 }

f3NetFpQosShaperEIRLo OBJECT-TYPE
    SYNTAX      Unsigned32
    MAX-ACCESS  read-create
    STATUS      current
    DESCRIPTION
       "This object represents the Excess Information Rate (EIR)
        (Lower 32 bits) of a Shaper."
    ::= { f3NetFpQosShaperEntry 7 }

f3NetFpQosShaperEIRHi OBJECT-TYPE
    SYNTAX      Unsigned32
    MAX-ACCESS  read-create
    STATUS      current
    DESCRIPTION
       "This object represents the Excess Information Rate (EIR)
        (Lower 32 bits) of a Shaper."
    ::= { f3NetFpQosShaperEntry 8 }

f3NetFpQosShaperCBS OBJECT-TYPE
    SYNTAX      Unsigned32
    MAX-ACCESS  read-create
    STATUS      current
    DESCRIPTION
       "This object represents the Commited Burst Size (CBS) 
        of a Shaper."
    ::= { f3NetFpQosShaperEntry 9 }

f3NetFpQosShaperEBS OBJECT-TYPE
    SYNTAX      Unsigned32
    MAX-ACCESS  read-create
    STATUS      current
    DESCRIPTION
       "This object represents the Excess Burst Size (EBS) 
        of a Shaper."
    ::= { f3NetFpQosShaperEntry 10 }

f3NetFpQosShaperBufferSize OBJECT-TYPE
    SYNTAX      Unsigned32
    MAX-ACCESS  read-create
    STATUS      current
    DESCRIPTION
       "This object represents the Buffer Size of the Shaper."
    ::= { f3NetFpQosShaperEntry 11 }

f3NetFpQosShaperCOS OBJECT-TYPE
    SYNTAX      Integer32 (0..7)
    MAX-ACCESS  read-only
    STATUS      current
    DESCRIPTION
       "This object provides the COS (Class of Service) value for
        the QOS Shaper."
    ::= { f3NetFpQosShaperEntry 12 }

f3NetFpQosShaperStorageType OBJECT-TYPE
    SYNTAX      StorageType
    MAX-ACCESS  read-create
    STATUS      current
    DESCRIPTION
       "The type of storage configured for this entry."
    ::= { f3NetFpQosShaperEntry 13 }

f3NetFpQosShaperRowStatus OBJECT-TYPE
    SYNTAX      RowStatus
    MAX-ACCESS  read-create
    STATUS      current
    DESCRIPTION
       "The status of this row.
        An entry MUST NOT exist in the active state unless all
        objects in the entry have an appropriate value, as described
        in the description clause for each writable object.

        The values of f3NetFpQosShaperRowStatus supported are
        createAndGo(4) and destroy(6). All mandatory attributes
        must be specified in a single SNMP SET request with
        f3NetFpQosShaperRowStatus value as createAndGo(4).
        Upon successful row creation, this object has a
        value of active(1).

        The f3NetFpQosShaperRowStatus object may be modified if
        the associated instance of this object is equal to active(1)."
    ::= { f3NetFpQosShaperEntry 14 }

--
--  Net Flow Point QoS Policer
--

f3NetFpQosPolicerTable  OBJECT-TYPE
    SYNTAX      SEQUENCE OF F3NetFpQosPolicerEntry
    MAX-ACCESS  not-accessible
    STATUS      current
    DESCRIPTION
       "A list of entries corresponding to Net Flow Point
        Quality of Service Policer for configuration purposes."
    ::= { f3FpmConfigObjects 9 }

f3NetFpQosPolicerEntry OBJECT-TYPE
    SYNTAX      F3NetFpQosPolicerEntry 
    MAX-ACCESS  not-accessible
    STATUS      current
    DESCRIPTION
       "A conceptual row in the f3NetFpQosPolicerTable. 
        These entries represent an Net Flow Point Quality
        of Service Policer."
    INDEX { neIndex, shelfIndex, slotIndex, cmEthernetNetPortIndex, 
            f3NetFlowPointIndex, f3NetFpQosPolicerIndex }
    ::= { f3NetFpQosPolicerTable 1 }

F3NetFpQosPolicerEntry ::= SEQUENCE {
    f3NetFpQosPolicerIndex                 Integer32,

    f3NetFpQosPolicerAdminState            AdminState,
    f3NetFpQosPolicerOperationalState      OperationalState,
    f3NetFpQosPolicerSecondaryState        SecondaryState,

    f3NetFpQosPolicerCIRLo                 Unsigned32,
    f3NetFpQosPolicerCIRHi                 Unsigned32,
    f3NetFpQosPolicerEIRLo                 Unsigned32,
    f3NetFpQosPolicerEIRHi                 Unsigned32,
    f3NetFpQosPolicerCBS                   Integer32,
    f3NetFpQosPolicerEBS                   Integer32,
    
    f3NetFpQosPolicerAlgorithm             PolicerAlgorithmType,
    f3NetFpQosPolicerColorMode             PolicerColorMode,
    f3NetFpQosPolicerCouplingFlag          TruthValue,
    f3NetFpQosPolicerPolicingEnabled       TruthValue,
    
    f3NetFpQosPolicerStorageType           StorageType,
    f3NetFpQosPolicerRowStatus             RowStatus 
}

f3NetFpQosPolicerIndex OBJECT-TYPE
    SYNTAX      Integer32 (1..8)
    MAX-ACCESS  not-accessible
    STATUS      current
    DESCRIPTION
       "The unique integer index value corresponding to a Quality 
        of Service Policer.
        The Policer Index represents the COS level. This
        is applicable in case of a Multi COS Flow Point. Index 1
        represents COS 0; Index 2 represents COS 1 and so on."
    ::= { f3NetFpQosPolicerEntry 1 }

f3NetFpQosPolicerAdminState OBJECT-TYPE
    SYNTAX      AdminState 
    MAX-ACCESS  read-create
    STATUS      current
    DESCRIPTION
       "This object represents the Administrative State of a Policer."
    ::= { f3NetFpQosPolicerEntry 2 }

f3NetFpQosPolicerOperationalState OBJECT-TYPE
    SYNTAX      OperationalState 
    MAX-ACCESS  read-only
    STATUS      current
    DESCRIPTION
       "This object represents the Operational State of a Policer." 
    ::= { f3NetFpQosPolicerEntry 3 }

f3NetFpQosPolicerSecondaryState OBJECT-TYPE
    SYNTAX      SecondaryState 
    MAX-ACCESS  read-only
    STATUS      current
    DESCRIPTION
       "This object represents the Secondary State of a Policer." 
    ::= { f3NetFpQosPolicerEntry 4 }

f3NetFpQosPolicerCIRLo OBJECT-TYPE
    SYNTAX      Unsigned32
    MAX-ACCESS  read-create
    STATUS      current
    DESCRIPTION
       "This object represents the Commited Information Rate (CIR)
        (Lower 32 bits) of the Policer."
    ::= { f3NetFpQosPolicerEntry 5 }

f3NetFpQosPolicerCIRHi OBJECT-TYPE
    SYNTAX      Unsigned32
    MAX-ACCESS  read-create
    STATUS      current
    DESCRIPTION
       "This object represents the Commited Information Rate (CIR)
        (Higher 32 bits) of the Policer."
    ::= { f3NetFpQosPolicerEntry 6 }

f3NetFpQosPolicerEIRLo OBJECT-TYPE
    SYNTAX      Unsigned32
    MAX-ACCESS  read-create
    STATUS      current
    DESCRIPTION
       "This object represents the Excess Information Rate (EIR)
        (Lower 32 bits) of a Policer."
    ::= { f3NetFpQosPolicerEntry 7 }

f3NetFpQosPolicerEIRHi OBJECT-TYPE
    SYNTAX      Unsigned32
    MAX-ACCESS  read-create
    STATUS      current
    DESCRIPTION
       "This object represents the Excess Information Rate (EIR)
        (Lower 32 bits) of a Policer."
    ::= { f3NetFpQosPolicerEntry 8 }

f3NetFpQosPolicerCBS OBJECT-TYPE
    SYNTAX      Integer32
    MAX-ACCESS  read-create
    STATUS      current
    DESCRIPTION
       "This object represents the Commited Burst Size (CBS) 
        of a Policer."
    ::= { f3NetFpQosPolicerEntry 9 }

f3NetFpQosPolicerEBS OBJECT-TYPE
    SYNTAX      Integer32
    MAX-ACCESS  read-create
    STATUS      current
    DESCRIPTION
       "This object represents the Excess Burst Size (EBS) 
        of a Policer."
    ::= { f3NetFpQosPolicerEntry 10 }

f3NetFpQosPolicerAlgorithm OBJECT-TYPE
    SYNTAX      PolicerAlgorithmType 
    MAX-ACCESS  read-only
    STATUS      current
    DESCRIPTION
       "This object represents Policer algorithm as 'srTCM'
        (Single Rate Triple Color Marking) or 'trTCM' 
        (Two Rate Triple Color Marking)."
    ::= { f3NetFpQosPolicerEntry 11 }

f3NetFpQosPolicerColorMode OBJECT-TYPE
    SYNTAX      PolicerColorMode 
    MAX-ACCESS  read-create
    STATUS      current
    DESCRIPTION
       "This object allows specification of Policer Color Mode as
        'color-aware' or 'color-blind'."
    ::= { f3NetFpQosPolicerEntry 12 }

f3NetFpQosPolicerCouplingFlag OBJECT-TYPE
    SYNTAX      TruthValue
    MAX-ACCESS  read-create
    STATUS      current
    DESCRIPTION
       "This object allows specification of Policer Coupling Flag.
        When coupling is enabled, tokens that would normally be 
        added to the C-bucket are passed to the E-bucket only once the CIR
        bucket has reached its CBS level. Therefore under this condition
        the E-bucket is being filled at the rate of CIR + EIR. 
        Normally the long term average of frames declared yellow is 
        bounded by the EIR. Coupling is a function to allow the 
        long term average of frames declared yellow to be bounded by 
        CIR + EIR. This allows a higher volume of yellow frames 
        to be delivered/received if the arrival of green marked frames 
        is low. Tokens from the E-bucket do NOT get passed to the 
        C-bucket once the EBS level has been reached.
        Enabling coupling in combination with a provisioned EIR of 0 
        allows for a single rate three color marking (srTCM) algorithm 
        to be established.  In this situation the E-bucket is filled at the 
        CIR rate in the case the C-bucket is filled to its CBS level."
    ::= { f3NetFpQosPolicerEntry 13 }

f3NetFpQosPolicerPolicingEnabled OBJECT-TYPE
    SYNTAX      TruthValue
    MAX-ACCESS  read-create
    STATUS      current
    DESCRIPTION
       "This object allows specification of Policer Policing.
        When Policing is disabled, traffic policing is bypassed. 
        When Policing is enabled, traffic policing is applied."
    ::= { f3NetFpQosPolicerEntry 14 }

f3NetFpQosPolicerStorageType OBJECT-TYPE
    SYNTAX      StorageType
    MAX-ACCESS  read-create
    STATUS      current
    DESCRIPTION
       "The type of storage configured for this entry."
    ::= { f3NetFpQosPolicerEntry 15 }

f3NetFpQosPolicerRowStatus OBJECT-TYPE
    SYNTAX      RowStatus
    MAX-ACCESS  read-create
    STATUS      current
    DESCRIPTION
       "The status of this row.
        An entry MUST NOT exist in the active state unless all
        objects in the entry have an appropriate value, as described
        in the description clause for each writable object.

        The values of f3NetFpQosPolicerRowStatus supported are
        createAndGo(4) and destroy(6). All mandatory attributes
        must be specified in a single SNMP SET request with
        f3NetFpQosPolicerRowStatus value as createAndGo(4).
        Upon successful row creation, this object has a
        value of active(1).

        The f3NetFpQosPolicerRowStatus object may be modified if
        the associated instance of this object is equal to active(1)."
    ::= { f3NetFpQosPolicerEntry 16 }

--
--  Net Flow Point Control Protocol Disposition 
--

f3NetFlowPointCpdV2Table  OBJECT-TYPE
    SYNTAX      SEQUENCE OF F3NetFlowPointCpdV2Entry
    MAX-ACCESS  not-accessible
    STATUS      current
    DESCRIPTION
       "A list of entries corresponding to Net Flow Point
        Control Protocol Disposition V2."
    ::= { f3FpmConfigObjects 10 }

f3NetFlowPointCpdV2Entry OBJECT-TYPE
    SYNTAX      F3NetFlowPointCpdV2Entry 
    MAX-ACCESS  not-accessible
    STATUS      current
    DESCRIPTION
       "A conceptual row in the f3NetFlowPointCpdV2Table. 
        These entries represent a Control Protocol Disposition 
        filtering criteria on the Net Flow Point."
    INDEX { neIndex, shelfIndex, slotIndex, cmEthernetNetPortIndex, 
            f3NetFlowPointIndex, f3NetFlowPointCpdV2Index }
    ::= { f3NetFlowPointCpdV2Table 1 }

F3NetFlowPointCpdV2Entry ::= SEQUENCE {
    f3NetFlowPointCpdV2Index                     Integer32,
    f3NetFlowPointCpdV2IslDispType               CmControlProtocolDispType,
    f3NetFlowPointCpdV2PagpDispType              CmControlProtocolDispType,
    f3NetFlowPointCpdV2UdldDispType              CmControlProtocolDispType,
    f3NetFlowPointCpdV2CdpDispType               CmControlProtocolDispType,
    f3NetFlowPointCpdV2VtpDispType               CmControlProtocolDispType,
    f3NetFlowPointCpdV2DtpDispType               CmControlProtocolDispType,
    f3NetFlowPointCpdV2PvstpPlusDispType         CmControlProtocolDispType,
    f3NetFlowPointCpdV2UplinkFastDispType        CmControlProtocolDispType,
    f3NetFlowPointCpdV2VlanBridgeDispType        CmControlProtocolDispType,
    f3NetFlowPointCpdV2L2PTDispType              CmControlProtocolDispType,
    f3NetFlowPointCpdV2BPDUDispType              CmControlProtocolDispType,
    f3NetFlowPointCpdV2PauseDispType             CmControlProtocolDispType,
    f3NetFlowPointCpdV2LACPDispType              CmControlProtocolDispType,
    f3NetFlowPointCpdV2LACPMarkerDispType        CmControlProtocolDispType,
    f3NetFlowPointCpdV2EfmOamDispType            CmControlProtocolDispType,
    f3NetFlowPointCpdV2SSMDispType               CmControlProtocolDispType,
    f3NetFlowPointCpdV2PortAuthenDispType        CmControlProtocolDispType,
    f3NetFlowPointCpdV2LANBridgesDispType        CmControlProtocolDispType,
    f3NetFlowPointCpdV2GMRPDispType              CmControlProtocolDispType,
    f3NetFlowPointCpdV2GVRPDispType              CmControlProtocolDispType,
    f3NetFlowPointCpdV2GARPDispType              CmControlProtocolDispType,
    f3NetFlowPointCpdV2ActiveControlProtocols    CmActiveControlProtocolsType,
    f3NetFlowPointCpdV2ELMIDispType              CmControlProtocolDispType,
    f3NetFlowPointCpdV2Mac00DispType             CmControlProtocolDispType,
    f3NetFlowPointCpdV2Mac01DispType             CmControlProtocolDispType,
    f3NetFlowPointCpdV2Mac02DispType             CmControlProtocolDispType,
    f3NetFlowPointCpdV2Mac03DispType             CmControlProtocolDispType,
    f3NetFlowPointCpdV2Mac04DispType             CmControlProtocolDispType,
    f3NetFlowPointCpdV2Mac05DispType             CmControlProtocolDispType,
    f3NetFlowPointCpdV2Mac06DispType             CmControlProtocolDispType,
    f3NetFlowPointCpdV2Mac07DispType             CmControlProtocolDispType,
    f3NetFlowPointCpdV2Mac08DispType             CmControlProtocolDispType,
    f3NetFlowPointCpdV2Mac09DispType             CmControlProtocolDispType,
    f3NetFlowPointCpdV2Mac0ADispType             CmControlProtocolDispType,
    f3NetFlowPointCpdV2Mac0BDispType             CmControlProtocolDispType,
    f3NetFlowPointCpdV2Mac0CDispType             CmControlProtocolDispType,
    f3NetFlowPointCpdV2Mac0DDispType             CmControlProtocolDispType,
    f3NetFlowPointCpdV2Mac0EDispType             CmControlProtocolDispType,
    f3NetFlowPointCpdV2Mac0FDispType             CmControlProtocolDispType,
    f3NetFlowPointCpdV2NearestLLDPDispType       CmControlProtocolDispType,
    f3NetFlowPointCpdV2NonTpmrLLDPDispType       CmControlProtocolDispType,
    f3NetFlowPointCpdV2CustomerLLDPDispType      CmControlProtocolDispType
}

f3NetFlowPointCpdV2Index OBJECT-TYPE
    SYNTAX      Integer32 
    MAX-ACCESS  not-accessible
    STATUS      current
    DESCRIPTION
       "Unique Index value to access the CPD row."
    ::= { f3NetFlowPointCpdV2Entry 1 }

f3NetFlowPointCpdV2IslDispType OBJECT-TYPE
    SYNTAX      CmControlProtocolDispType 
    MAX-ACCESS  read-write
    STATUS      current
    DESCRIPTION
       "Control Protocol Disposition for ISL (Inter Switch Link).
        MAC Address (01:00:0C:00:00:00)."
    ::= { f3NetFlowPointCpdV2Entry 2 }

f3NetFlowPointCpdV2PagpDispType OBJECT-TYPE
    SYNTAX      CmControlProtocolDispType 
    MAX-ACCESS  read-write
    STATUS      current
    DESCRIPTION
       "Control Protocol Disposition for PAGP (Port Aggregation Protocol).
        MAC Address (01:00:0C:CC:CC:CC), Ethertype(0x104)."
    ::= { f3NetFlowPointCpdV2Entry 3 }

f3NetFlowPointCpdV2UdldDispType OBJECT-TYPE
    SYNTAX      CmControlProtocolDispType 
    MAX-ACCESS  read-write
    STATUS      current
    DESCRIPTION
       "Control Protocol Disposition for UDLD (Unidirectional Link Detection).
        MAC Address (01:00:0C:CC:CC:CC), Ethertype(0x111)."
    ::= { f3NetFlowPointCpdV2Entry 4 }

f3NetFlowPointCpdV2CdpDispType OBJECT-TYPE
    SYNTAX      CmControlProtocolDispType 
    MAX-ACCESS  read-write
    STATUS      current
    DESCRIPTION
       "Control Protocol Disposition for CDP (Cisco Discovery Protocol).
        MAC Address (01:00:0C:CC:CC:CC), Ethertype(0x2000)."
    ::= { f3NetFlowPointCpdV2Entry 5 }

f3NetFlowPointCpdV2VtpDispType OBJECT-TYPE
    SYNTAX      CmControlProtocolDispType 
    MAX-ACCESS  read-write
    STATUS      current
    DESCRIPTION
       "Control Protocol Disposition for VTP (VLAN Trunking Protocol).
        MAC Address (01:00:0C:CC:CC:CC), Ethertype(0x2003)."
    ::= { f3NetFlowPointCpdV2Entry 6 }

f3NetFlowPointCpdV2DtpDispType OBJECT-TYPE
    SYNTAX      CmControlProtocolDispType 
    MAX-ACCESS  read-write
    STATUS      current
    DESCRIPTION
       "Control Protocol Disposition for DTP (Dynamic Trunking).
        MAC Address (01:00:0C:CC:CC:CC), Ethertype(0x2004)."
    ::= { f3NetFlowPointCpdV2Entry 7 }

f3NetFlowPointCpdV2PvstpPlusDispType OBJECT-TYPE
    SYNTAX      CmControlProtocolDispType 
    MAX-ACCESS  read-write
    STATUS      current
    DESCRIPTION
       "Control Protocol Disposition for Spanning Tree PVSTP+.
        MAC Address (01:00:0C:CC:CC:CC), Ethertype(0x10B)."
    ::= { f3NetFlowPointCpdV2Entry 8 }

f3NetFlowPointCpdV2UplinkFastDispType OBJECT-TYPE
    SYNTAX      CmControlProtocolDispType 
    MAX-ACCESS  read-write
    STATUS      current
    DESCRIPTION
       "Control Protocol Disposition for STP UplinkFast.
        MAC Address (01:00:0C:CD:CD:CD), Ethertype(0x200A)."
    ::= { f3NetFlowPointCpdV2Entry 9 }

f3NetFlowPointCpdV2VlanBridgeDispType OBJECT-TYPE
    SYNTAX      CmControlProtocolDispType 
    MAX-ACCESS  read-write
    STATUS      current
    DESCRIPTION
       "Control Protocol Disposition for VLAN Bridge.
        MAC Address (01:00:0C:CD:CD:CE), Ethertype(0x10C)."
    ::= { f3NetFlowPointCpdV2Entry 10 }

f3NetFlowPointCpdV2L2PTDispType OBJECT-TYPE
    SYNTAX      CmControlProtocolDispType 
    MAX-ACCESS  read-write
    STATUS      current
    DESCRIPTION
       "Control Protocol Disposition for Layer 2 Protocol Tunnelling(L2PT).
        MAC Address (01:00:0C:CD:CD:D0)."
    ::= { f3NetFlowPointCpdV2Entry 11 }

f3NetFlowPointCpdV2BPDUDispType OBJECT-TYPE
    SYNTAX      CmControlProtocolDispType 
    MAX-ACCESS  read-write
    STATUS      current
    DESCRIPTION
       "Control Protocol Disposition for IEEE Spanning Tree(STP),
        MSTP (Multiple Spanning Tree) and RSTP (Rapid Reconfiguration of
        Spanning Tree). MAC Address (01:80:C2:00:00:00)."
    ::= { f3NetFlowPointCpdV2Entry 12 }

f3NetFlowPointCpdV2PauseDispType OBJECT-TYPE
    SYNTAX      CmControlProtocolDispType 
    MAX-ACCESS  read-write
    STATUS      current
    DESCRIPTION
       "Control Protocol Disposition for IEEE 802.3x Flow Control 
        (PAUSE frames)."
    ::= { f3NetFlowPointCpdV2Entry 13 }

f3NetFlowPointCpdV2LACPDispType OBJECT-TYPE
    SYNTAX      CmControlProtocolDispType 
    MAX-ACCESS  read-write
    STATUS      current
    DESCRIPTION
       "Control Protocol Disposition for 802.3ad Link Aggregation
        Protocol.
        MAC Address (01:80:C2:00:00:03), Ethertype (0x8809), Subtype(01)."
    ::= { f3NetFlowPointCpdV2Entry 14 }

f3NetFlowPointCpdV2LACPMarkerDispType OBJECT-TYPE
    SYNTAX      CmControlProtocolDispType 
    MAX-ACCESS  read-write
    STATUS      current
    DESCRIPTION
       "Control Protocol Disposition for IEEE 802.3ad Marker Protocol.
        MAC Address (01:80:C2:00:00:03), Ethertype (0x8809), Subtype(02)."
    ::= { f3NetFlowPointCpdV2Entry 15 }

f3NetFlowPointCpdV2EfmOamDispType OBJECT-TYPE
    SYNTAX      CmControlProtocolDispType 
    MAX-ACCESS  read-write
    STATUS      current
    DESCRIPTION
       "Control Protocol Disposition for IEEE 802.3ah EFM OAM.
        MAC Address (01:80:C2:00:00:03), Ethertype (0x8809), Subtype(03)."
    ::= { f3NetFlowPointCpdV2Entry 16 }

f3NetFlowPointCpdV2SSMDispType OBJECT-TYPE
    SYNTAX      CmControlProtocolDispType 
    MAX-ACCESS  read-write
    STATUS      current
    DESCRIPTION
       "Control Protocol Disposition for Sync Status Messages.
        MAC Address (01:80:C2:00:00:02), Ethertype (0x19A7), Subtype(0A)."
    ::= { f3NetFlowPointCpdV2Entry 17 }

f3NetFlowPointCpdV2PortAuthenDispType OBJECT-TYPE
    SYNTAX      CmControlProtocolDispType 
    MAX-ACCESS  read-write
    STATUS      current
    DESCRIPTION
       "Control Protocol Disposition for IEEE 802.1x Protocol.
        MAC Address (01:80:C2:00:00:03), Ethertype (0x888E)."
    ::= { f3NetFlowPointCpdV2Entry 18 }

f3NetFlowPointCpdV2LANBridgesDispType OBJECT-TYPE
    SYNTAX      CmControlProtocolDispType 
    MAX-ACCESS  read-write
    STATUS      current
    DESCRIPTION
       "Control Protocol Disposition for IEEE 802.1d LAN Bridge Managment.
        MAC Address (01:80:C2:00:00:10)."
    ::= { f3NetFlowPointCpdV2Entry 19 }

f3NetFlowPointCpdV2GMRPDispType OBJECT-TYPE
    SYNTAX      CmControlProtocolDispType 
    MAX-ACCESS  read-write
    STATUS      current
    DESCRIPTION
       "Control Protocol Disposition for GARP Multicast Registration
        Protocol. MAC Address (01:80:C2:00:00:20)."
    ::= { f3NetFlowPointCpdV2Entry 20 }

f3NetFlowPointCpdV2GVRPDispType OBJECT-TYPE
    SYNTAX      CmControlProtocolDispType 
    MAX-ACCESS  read-write
    STATUS      current
    DESCRIPTION
       "Control Protocol Disposition for GARP VLAN Registration
        Protocol. MAC Address (01:80:C2:00:00:21)."
    ::= { f3NetFlowPointCpdV2Entry 21 }

f3NetFlowPointCpdV2GARPDispType OBJECT-TYPE
    SYNTAX      CmControlProtocolDispType 
    MAX-ACCESS  read-write
    STATUS      current
    DESCRIPTION
       "Group Disposition type which includes GARP Reserved 
        MAC Address from range 01:80:C2:00:00:22 to 01:80:C2:00:00:2F."
    ::= { f3NetFlowPointCpdV2Entry 22 }

f3NetFlowPointCpdV2ActiveControlProtocols OBJECT-TYPE
    SYNTAX      CmActiveControlProtocolsType
    MAX-ACCESS  read-only
    STATUS      current
    DESCRIPTION
       "List of Active Control Protocol Dispositions. Note that
        if the Port Level Disposition control is set to PEER or 
        DISCARD, the flow level disposition is no longer active.
        This object provides information on all the active
        dispositions."
    ::= { f3NetFlowPointCpdV2Entry 23 }

f3NetFlowPointCpdV2ELMIDispType OBJECT-TYPE
    SYNTAX      CmControlProtocolDispType 
    MAX-ACCESS  read-write
    STATUS      current
    DESCRIPTION
       "ELMI (Ethernet Local Management Interface) Disposition type. 
        MAC Address 01:80:C2:00:00:07 and EtherType of 0x88EE."
    ::= { f3NetFlowPointCpdV2Entry 24 }

f3NetFlowPointCpdV2Mac00DispType OBJECT-TYPE
    SYNTAX      CmControlProtocolDispType 
    MAX-ACCESS  read-write
    STATUS      current
    DESCRIPTION
       "MAC Address 01:80:C2:00:00:00 Disposition type."
    ::= { f3NetFlowPointCpdV2Entry 25 }

f3NetFlowPointCpdV2Mac01DispType OBJECT-TYPE
    SYNTAX      CmControlProtocolDispType 
    MAX-ACCESS  read-write
    STATUS      current
    DESCRIPTION
       "MAC Address 01:80:C2:00:00:01 Disposition type."
    ::= { f3NetFlowPointCpdV2Entry 26 }

f3NetFlowPointCpdV2Mac02DispType OBJECT-TYPE
    SYNTAX      CmControlProtocolDispType 
    MAX-ACCESS  read-write
    STATUS      current
    DESCRIPTION
       "MAC Address 01:80:C2:00:00:02 Disposition type."
    ::= { f3NetFlowPointCpdV2Entry 27 }

f3NetFlowPointCpdV2Mac03DispType OBJECT-TYPE
    SYNTAX      CmControlProtocolDispType 
    MAX-ACCESS  read-write
    STATUS      current
    DESCRIPTION
       "MAC Address 01:80:C2:00:00:03 Disposition type."
    ::= { f3NetFlowPointCpdV2Entry 28 }

f3NetFlowPointCpdV2Mac04DispType OBJECT-TYPE
    SYNTAX      CmControlProtocolDispType 
    MAX-ACCESS  read-write
    STATUS      current
    DESCRIPTION
       "MAC Address 01:80:C2:00:00:04 Disposition type."
    ::= { f3NetFlowPointCpdV2Entry 29 }

f3NetFlowPointCpdV2Mac05DispType OBJECT-TYPE
    SYNTAX      CmControlProtocolDispType 
    MAX-ACCESS  read-write
    STATUS      current
    DESCRIPTION
       "MAC Address 01:80:C2:00:00:05 Disposition type."
    ::= { f3NetFlowPointCpdV2Entry 30 }

f3NetFlowPointCpdV2Mac06DispType OBJECT-TYPE
    SYNTAX      CmControlProtocolDispType 
    MAX-ACCESS  read-write
    STATUS      current
    DESCRIPTION
       "MAC Address 01:80:C2:00:00:06 Disposition type."
    ::= { f3NetFlowPointCpdV2Entry 31 }

f3NetFlowPointCpdV2Mac07DispType OBJECT-TYPE
    SYNTAX      CmControlProtocolDispType 
    MAX-ACCESS  read-write
    STATUS      current
    DESCRIPTION
       "MAC Address 01:80:C2:00:00:07 Disposition type."
    ::= { f3NetFlowPointCpdV2Entry 32 }

f3NetFlowPointCpdV2Mac08DispType OBJECT-TYPE
    SYNTAX      CmControlProtocolDispType 
    MAX-ACCESS  read-write
    STATUS      current
    DESCRIPTION
       "MAC Address 01:80:C2:00:00:08 Disposition type."
    ::= { f3NetFlowPointCpdV2Entry 33 }

f3NetFlowPointCpdV2Mac09DispType OBJECT-TYPE
    SYNTAX      CmControlProtocolDispType 
    MAX-ACCESS  read-write
    STATUS      current
    DESCRIPTION
       "MAC Address 01:80:C2:00:00:09 Disposition type."
    ::= { f3NetFlowPointCpdV2Entry 34 }

f3NetFlowPointCpdV2Mac0ADispType OBJECT-TYPE
    SYNTAX      CmControlProtocolDispType 
    MAX-ACCESS  read-write
    STATUS      current
    DESCRIPTION
       "MAC Address 01:80:C2:00:00:0A Disposition type."
    ::= { f3NetFlowPointCpdV2Entry 35 }

f3NetFlowPointCpdV2Mac0BDispType OBJECT-TYPE
    SYNTAX      CmControlProtocolDispType 
    MAX-ACCESS  read-write
    STATUS      current
    DESCRIPTION
       "MAC Address 01:80:C2:00:00:0B Disposition type."
    ::= { f3NetFlowPointCpdV2Entry 36 }

f3NetFlowPointCpdV2Mac0CDispType OBJECT-TYPE
    SYNTAX      CmControlProtocolDispType 
    MAX-ACCESS  read-write
    STATUS      current
    DESCRIPTION
       "MAC Address 01:80:C2:00:00:0C Disposition type."
    ::= { f3NetFlowPointCpdV2Entry 37 }

f3NetFlowPointCpdV2Mac0DDispType OBJECT-TYPE
    SYNTAX      CmControlProtocolDispType 
    MAX-ACCESS  read-write
    STATUS      current
    DESCRIPTION
       "MAC Address 01:80:C2:00:00:0D Disposition type."
    ::= { f3NetFlowPointCpdV2Entry 38 }

f3NetFlowPointCpdV2Mac0EDispType OBJECT-TYPE
    SYNTAX      CmControlProtocolDispType 
    MAX-ACCESS  read-write
    STATUS      current
    DESCRIPTION
       "MAC Address 01:80:C2:00:00:0E Disposition type."
    ::= { f3NetFlowPointCpdV2Entry 39 }

f3NetFlowPointCpdV2Mac0FDispType OBJECT-TYPE
    SYNTAX      CmControlProtocolDispType 
    MAX-ACCESS  read-write
    STATUS      current
    DESCRIPTION
       "MAC Address 01:80:C2:00:00:0F Disposition type."
    ::= { f3NetFlowPointCpdV2Entry 40 }

f3NetFlowPointCpdV2NearestLLDPDispType OBJECT-TYPE
    SYNTAX      CmControlProtocolDispType 
    MAX-ACCESS  read-write
    STATUS      current
    DESCRIPTION
       "LLDP (Link Layer Discovery Protocol) Nearest Bridge Disposition type."
    ::= { f3NetFlowPointCpdV2Entry 41 }

f3NetFlowPointCpdV2NonTpmrLLDPDispType OBJECT-TYPE
    SYNTAX      CmControlProtocolDispType 
    MAX-ACCESS  read-write
    STATUS      current
    DESCRIPTION
       "LLDP (Link Layer Discovery Protocol) Non-TPMR Bridge Disposition type."
    ::= { f3NetFlowPointCpdV2Entry 42 }

f3NetFlowPointCpdV2CustomerLLDPDispType OBJECT-TYPE
    SYNTAX      CmControlProtocolDispType 
    MAX-ACCESS  read-write
    STATUS      current
    DESCRIPTION
       "LLDP (Link Layer Discovery Protocol) Customer Bridge Disposition type."
    ::= { f3NetFlowPointCpdV2Entry 43 }

--
--  Net Flowpoint table extension for Learning Control configuration
--
f3NetFlowPointLearningConfigTable  OBJECT-TYPE
    SYNTAX      SEQUENCE OF F3NetFlowPointLearningConfigEntry   
    MAX-ACCESS  not-accessible
    STATUS      current
    DESCRIPTION
            "This table extends f3NetFlowPointTable to provide parameters for MAC Table control
             configuration."
    ::= { f3FpmConfigObjects 11 }

f3NetFlowPointLearningConfigEntry  OBJECT-TYPE
    SYNTAX      F3NetFlowPointLearningConfigEntry   
    MAX-ACCESS  not-accessible
    STATUS      current
    DESCRIPTION
            "A conceptual row in the f3NetFlowPointLearningConfigTable."
    AUGMENTS { f3NetFlowPointEntry }
    ::= { f3NetFlowPointLearningConfigTable 1 }

F3NetFlowPointLearningConfigEntry ::= SEQUENCE {
    f3NetFlowPointLearningConfigLearningEnabled       TruthValue,
    f3NetFlowPointLearningConfigMaxFwdEntries         Integer32,
    f3NetFlowPointLearningConfigProtectLearningCtrl   ProtectLearningControl,
    f3NetFlowPointLearningConfigAction                FlowLearningConfigAction
}

f3NetFlowPointLearningConfigLearningEnabled OBJECT-TYPE
    SYNTAX        TruthValue
    MAX-ACCESS    read-write
    STATUS        current
    DESCRIPTION
         "This object allows configuring Learning Control on this Flowpoint."
    ::= { f3NetFlowPointLearningConfigEntry 1 }

f3NetFlowPointLearningConfigMaxFwdEntries OBJECT-TYPE
    SYNTAX        Integer32
    MAX-ACCESS    read-write
    STATUS        current
    DESCRIPTION
         "This object allows configuring the maximum number of Forwarding Entries 
          on this Flowpoint."
    ::= { f3NetFlowPointLearningConfigEntry 2 }

f3NetFlowPointLearningConfigProtectLearningCtrl OBJECT-TYPE
    SYNTAX        ProtectLearningControl
    MAX-ACCESS    read-write
    STATUS        current
    DESCRIPTION
         "This object allows configuring Learning Control on this Flowpoint."
    ::= { f3NetFlowPointLearningConfigEntry 3 }

f3NetFlowPointLearningConfigAction OBJECT-TYPE
    SYNTAX        FlowLearningConfigAction
    MAX-ACCESS    read-write
    STATUS        current
    DESCRIPTION
         "This objects allows performing user action on Flow Learning Table."
    ::= { f3NetFlowPointLearningConfigEntry 4 }

--
--  FPM Access Port FP QoS Shaper
--
f3AccPortFpQosShaperTable OBJECT-TYPE
    SYNTAX      SEQUENCE OF F3AccPortFpQosShaperEntry
    MAX-ACCESS  not-accessible
    STATUS      current
    DESCRIPTION
       "A list of entries corresponding to Access Port 
        Quality of Service Shaper for configuration purposes."
    ::= { f3FpmConfigObjects 12 }

f3AccPortFpQosShaperEntry OBJECT-TYPE
    SYNTAX      F3AccPortFpQosShaperEntry 
    MAX-ACCESS  not-accessible
    STATUS      current
    DESCRIPTION
       "A conceptual row in the f3AccPortFpQosShaperTable. 
        These entries represent an Access Port Quality 
        of Service Shaper."
    INDEX { neIndex, shelfIndex, slotIndex, cmEthernetAccPortIndex, 
            f3AccPortFpQosShaperIndex }
    ::= { f3AccPortFpQosShaperTable 1 }

F3AccPortFpQosShaperEntry ::= SEQUENCE {
    f3AccPortFpQosShaperIndex               Integer32,

    f3AccPortFpQosShaperAdminState          AdminState,
    f3AccPortFpQosShaperOperationalState    OperationalState,
    f3AccPortFpQosShaperSecondaryState      SecondaryState,

    f3AccPortFpQosShaperCIRLo               Unsigned32,
    f3AccPortFpQosShaperCIRHi               Unsigned32,
    f3AccPortFpQosShaperEIRLo               Unsigned32,
    f3AccPortFpQosShaperEIRHi               Unsigned32,
    f3AccPortFpQosShaperCBS                 Unsigned32,
    f3AccPortFpQosShaperEBS                 Unsigned32,
    f3AccPortFpQosShaperBufferSize          Unsigned32,
    f3AccPortFpQosShaperCOS                 Integer32,
    
    f3AccPortFpQosShaperStorageType         StorageType,
    f3AccPortFpQosShaperRowStatus           RowStatus
}

f3AccPortFpQosShaperIndex OBJECT-TYPE
    SYNTAX      Integer32 (1..8)
    MAX-ACCESS  not-accessible
    STATUS      current
    DESCRIPTION
       "The unique integer index value corresponding to a Quality 
        of Service Shaper."
    ::= { f3AccPortFpQosShaperEntry 1 }

f3AccPortFpQosShaperAdminState OBJECT-TYPE
    SYNTAX      AdminState 
    MAX-ACCESS  read-create
    STATUS      current
    DESCRIPTION
       "This object represents the Administrative State of a Shaper." 
    ::= { f3AccPortFpQosShaperEntry 2 }

f3AccPortFpQosShaperOperationalState OBJECT-TYPE
    SYNTAX      OperationalState 
    MAX-ACCESS  read-only
    STATUS      current
    DESCRIPTION
       "This object represents the Operational State of a Shaper." 
    ::= { f3AccPortFpQosShaperEntry 3 }

f3AccPortFpQosShaperSecondaryState OBJECT-TYPE
    SYNTAX      SecondaryState 
    MAX-ACCESS  read-only
    STATUS      current
    DESCRIPTION
       "This object represents the Secondary State of the Shaper." 
    ::= { f3AccPortFpQosShaperEntry 4 }

f3AccPortFpQosShaperCIRLo OBJECT-TYPE
    SYNTAX      Unsigned32
    MAX-ACCESS  read-create
    STATUS      current
    DESCRIPTION
       "This object represents the Commited Information Rate (CIR)
        (Lower 32 bits) of the Shaper."
    ::= { f3AccPortFpQosShaperEntry 5 }
     
f3AccPortFpQosShaperCIRHi OBJECT-TYPE
    SYNTAX      Unsigned32
    MAX-ACCESS  read-create
    STATUS      current
    DESCRIPTION
       "This object represents the Commited Information Rate (CIR)
        (Higher 32 bits) of the Shaper."
    ::= { f3AccPortFpQosShaperEntry 6 }

f3AccPortFpQosShaperEIRLo OBJECT-TYPE
    SYNTAX      Unsigned32
    MAX-ACCESS  read-create
    STATUS      current
    DESCRIPTION
       "This object represents the Excess Information Rate (EIR)
        (Lower 32 bits) of a Shaper."
    ::= { f3AccPortFpQosShaperEntry 7 }

f3AccPortFpQosShaperEIRHi OBJECT-TYPE
    SYNTAX      Unsigned32
    MAX-ACCESS  read-create
    STATUS      current
    DESCRIPTION
       "This object represents the Excess Information Rate (EIR)
        (Lower 32 bits) of a Shaper."
    ::= { f3AccPortFpQosShaperEntry 8 }

f3AccPortFpQosShaperCBS OBJECT-TYPE
    SYNTAX      Unsigned32
    MAX-ACCESS  read-create
    STATUS      current
    DESCRIPTION
       "This object represents the Commited Burst Size (CBS) 
        of a Shaper."
    ::= { f3AccPortFpQosShaperEntry 9 }

f3AccPortFpQosShaperEBS OBJECT-TYPE
    SYNTAX      Unsigned32
    MAX-ACCESS  read-create
    STATUS      current
    DESCRIPTION
       "This object represents the Excess Burst Size (EBS) 
        of a Shaper."
    ::= { f3AccPortFpQosShaperEntry 10 }

f3AccPortFpQosShaperBufferSize OBJECT-TYPE
    SYNTAX      Unsigned32
    MAX-ACCESS  read-create
    STATUS      current
    DESCRIPTION
       "This object represents the Buffer Size of the Shaper."
    ::= { f3AccPortFpQosShaperEntry 11 }

f3AccPortFpQosShaperCOS OBJECT-TYPE
    SYNTAX      Integer32 (0..7)
    MAX-ACCESS  read-only
    STATUS      current
    DESCRIPTION
       "This object provides the COS (Class of Service) value for
        the QOS Shaper."
    ::= { f3AccPortFpQosShaperEntry 12 }

f3AccPortFpQosShaperStorageType OBJECT-TYPE
    SYNTAX      StorageType
    MAX-ACCESS  read-create
    STATUS      current
    DESCRIPTION
       "The type of storage configured for this entry."
    ::= { f3AccPortFpQosShaperEntry 13 }

f3AccPortFpQosShaperRowStatus OBJECT-TYPE
    SYNTAX      RowStatus
    MAX-ACCESS  read-create
    STATUS      current
    DESCRIPTION
       "The status of this row.
        An entry MUST NOT exist in the active state unless all
        objects in the entry have an appropriate value, as described
        in the description clause for each writable object.

        The values of f3AccPortFpQosShaperRowStatus supported are
        createAndGo(4) and destroy(6). All mandatory attributes
        must be specified in a single SNMP SET request with
        f3AccPortFpQosShaperRowStatus value as createAndGo(4).
        Upon successful row creation, this object has a
        value of active(1).

        The f3AccPortFpQosShaperRowStatus object may be modified if
        the associated instance of this object is equal to active(1)."
    ::= { f3AccPortFpQosShaperEntry 14 }

--
--  FPM Network Port QoS Shaper
--
f3NetPortFpQosShaperTable OBJECT-TYPE
    SYNTAX      SEQUENCE OF F3NetPortFpQosShaperEntry
    MAX-ACCESS  not-accessible
    STATUS      current
    DESCRIPTION
       "A list of entries corresponding to Network Port 
        Quality of Service Shaper for configuration purposes."
    ::= { f3FpmConfigObjects 13 }

f3NetPortFpQosShaperEntry OBJECT-TYPE
    SYNTAX      F3NetPortFpQosShaperEntry 
    MAX-ACCESS  not-accessible
    STATUS      current
    DESCRIPTION
       "A conceptual row in the f3NetPortFpQosShaperTable. 
        These entries represent an Network Port Quality 
        of Service Shaper."
    INDEX { neIndex, shelfIndex, slotIndex, cmEthernetNetPortIndex, 
            f3NetPortFpQosShaperIndex }
    ::= { f3NetPortFpQosShaperTable 1 }

F3NetPortFpQosShaperEntry ::= SEQUENCE {
    f3NetPortFpQosShaperIndex               Integer32,

    f3NetPortFpQosShaperAdminState          AdminState,
    f3NetPortFpQosShaperOperationalState    OperationalState,
    f3NetPortFpQosShaperSecondaryState      SecondaryState,

    f3NetPortFpQosShaperCIRLo               Unsigned32,
    f3NetPortFpQosShaperCIRHi               Unsigned32,
    f3NetPortFpQosShaperEIRLo               Unsigned32,
    f3NetPortFpQosShaperEIRHi               Unsigned32,
    f3NetPortFpQosShaperCBS                 Unsigned32,
    f3NetPortFpQosShaperEBS                 Unsigned32,
    f3NetPortFpQosShaperBufferSize          Unsigned32,
    f3NetPortFpQosShaperCOS                 Integer32,
    
    f3NetPortFpQosShaperStorageType         StorageType,
    f3NetPortFpQosShaperRowStatus           RowStatus
}

f3NetPortFpQosShaperIndex OBJECT-TYPE
    SYNTAX      Integer32 (1..8)
    MAX-ACCESS  not-accessible
    STATUS      current
    DESCRIPTION
       "The unique integer index value corresponding to a Quality 
        of Service Shaper."
    ::= { f3NetPortFpQosShaperEntry 1 }

f3NetPortFpQosShaperAdminState OBJECT-TYPE
    SYNTAX      AdminState 
    MAX-ACCESS  read-create
    STATUS      current
    DESCRIPTION
       "This object represents the Administrative State of a Shaper." 
    ::= { f3NetPortFpQosShaperEntry 2 }

f3NetPortFpQosShaperOperationalState OBJECT-TYPE
    SYNTAX      OperationalState 
    MAX-ACCESS  read-only
    STATUS      current
    DESCRIPTION
       "This object represents the Operational State of a Shaper." 
    ::= { f3NetPortFpQosShaperEntry 3 }

f3NetPortFpQosShaperSecondaryState OBJECT-TYPE
    SYNTAX      SecondaryState 
    MAX-ACCESS  read-only
    STATUS      current
    DESCRIPTION
       "This object represents the Secondary State of the Shaper." 
    ::= { f3NetPortFpQosShaperEntry 4 }

f3NetPortFpQosShaperCIRLo OBJECT-TYPE
    SYNTAX      Unsigned32
    MAX-ACCESS  read-create
    STATUS      current
    DESCRIPTION
       "This object represents the Commited Information Rate (CIR)
        (Lower 32 bits) of the Shaper."
    ::= { f3NetPortFpQosShaperEntry 5 }
     
f3NetPortFpQosShaperCIRHi OBJECT-TYPE
    SYNTAX      Unsigned32
    MAX-ACCESS  read-create
    STATUS      current
    DESCRIPTION
       "This object represents the Commited Information Rate (CIR)
        (Higher 32 bits) of the Shaper."
    ::= { f3NetPortFpQosShaperEntry 6 }

f3NetPortFpQosShaperEIRLo OBJECT-TYPE
    SYNTAX      Unsigned32
    MAX-ACCESS  read-create
    STATUS      current
    DESCRIPTION
       "This object represents the Excess Information Rate (EIR)
        (Lower 32 bits) of a Shaper."
    ::= { f3NetPortFpQosShaperEntry 7 }

f3NetPortFpQosShaperEIRHi OBJECT-TYPE
    SYNTAX      Unsigned32
    MAX-ACCESS  read-create
    STATUS      current
    DESCRIPTION
       "This object represents the Excess Information Rate (EIR)
        (Lower 32 bits) of a Shaper."
    ::= { f3NetPortFpQosShaperEntry 8 }

f3NetPortFpQosShaperCBS OBJECT-TYPE
    SYNTAX      Unsigned32
    MAX-ACCESS  read-create
    STATUS      current
    DESCRIPTION
       "This object represents the Commited Burst Size (CBS) 
        of a Shaper."
    ::= { f3NetPortFpQosShaperEntry 9 }

f3NetPortFpQosShaperEBS OBJECT-TYPE
    SYNTAX      Unsigned32
    MAX-ACCESS  read-create
    STATUS      current
    DESCRIPTION
       "This object represents the Excess Burst Size (EBS) 
        of a Shaper."
    ::= { f3NetPortFpQosShaperEntry 10 }

f3NetPortFpQosShaperBufferSize OBJECT-TYPE
    SYNTAX      Unsigned32
    MAX-ACCESS  read-create
    STATUS      current
    DESCRIPTION
       "This object represents the Buffer Size of the Shaper."
    ::= { f3NetPortFpQosShaperEntry 11 }

f3NetPortFpQosShaperCOS OBJECT-TYPE
    SYNTAX      Integer32 (0..7)
    MAX-ACCESS  read-only
    STATUS      current
    DESCRIPTION
       "This object provides the COS (Class of Service) value for
        the QOS Shaper."
    ::= { f3NetPortFpQosShaperEntry 12 }

f3NetPortFpQosShaperStorageType OBJECT-TYPE
    SYNTAX      StorageType
    MAX-ACCESS  read-create
    STATUS      current
    DESCRIPTION
       "The type of storage configured for this entry."
    ::= { f3NetPortFpQosShaperEntry 13 }

f3NetPortFpQosShaperRowStatus OBJECT-TYPE
    SYNTAX      RowStatus
    MAX-ACCESS  read-create
    STATUS      current
    DESCRIPTION
       "The status of this row.
        An entry MUST NOT exist in the active state unless all
        objects in the entry have an appropriate value, as described
        in the description clause for each writable object.

        The values of f3NetPortFpQosShaperRowStatus supported are
        createAndGo(4) and destroy(6). All mandatory attributes
        must be specified in a single SNMP SET request with
        f3NetPortFpQosShaperRowStatus value as createAndGo(4).
        Upon successful row creation, this object has a
        value of active(1).

        The f3NetPortFpQosShaperRowStatus object may be modified if
        the associated instance of this object is equal to active(1)."
    ::= { f3NetPortFpQosShaperEntry 14 }

--
-- Access Flowpoint Current Statistics Table
--

f3AccFlowPointStatsTable OBJECT-TYPE
    SYNTAX      SEQUENCE OF F3AccFlowPointStatsEntry
    MAX-ACCESS  not-accessible
    STATUS      current
    DESCRIPTION
            "A collection of FlowPoint statistics.  
             These reflect the current data."
    ::= { f3FpmPerfObjects 1 }

f3AccFlowPointStatsEntry OBJECT-TYPE
    SYNTAX      F3AccFlowPointStatsEntry 
    MAX-ACCESS  not-accessible
    STATUS      current
    DESCRIPTION
            "A conceptual row in the f3AccFlowPointStatsTable.
             Entries exist in this table for each FlowPoint."
    INDEX { neIndex, shelfIndex, slotIndex, cmEthernetAccPortIndex,
            f3AccFlowPointIndex, f3AccFlowPointStatsIndex }
    ::= { f3AccFlowPointStatsTable 1 }

F3AccFlowPointStatsEntry ::= SEQUENCE {
    f3AccFlowPointStatsIndex                 Integer32,
    f3AccFlowPointStatsIntervalType          CmPmIntervalType,
    f3AccFlowPointStatsValid                 TruthValue,
    f3AccFlowPointStatsAction                CmPmBinAction,
    f3AccFlowPointStatsL2CPFD                PerfCounter64,
    f3AccFlowPointStatsABRRx                 PerfCounter64,
    f3AccFlowPointStatsABRRLRx               PerfCounter64,
    f3AccFlowPointStatsUAS                   PerfCounter64,
    f3AccFlowPointStatsSES                   PerfCounter64, 
    f3AccFlowPointStatsFMG                   PerfCounter64,
    f3AccFlowPointStatsFMY                   PerfCounter64,
    f3AccFlowPointStatsFMRD                  PerfCounter64,
    f3AccFlowPointStatsFTD                   PerfCounter64,
    f3AccFlowPointStatsBytesIn               PerfCounter64,
    f3AccFlowPointStatsBytesOut              PerfCounter64,
    f3AccFlowPointStatsIBRMax                PerfCounter64,
    f3AccFlowPointStatsIBRRlMax              PerfCounter64,
    f3AccFlowPointStatsIBRMin                PerfCounter64,
    f3AccFlowPointStatsIBRRlMin              PerfCounter64,
    f3AccFlowPointStatsIBR                   PerfCounter64,
    f3AccFlowPointStatsIBRRl                 PerfCounter64,
    f3AccFlowPointStatsFBCD                  PerfCounter64,
    f3AccFlowPointStatsFMCD                  PerfCounter64,
    f3AccFlowPointStatsFdRxFb                PerfCounter64,
    f3AccFlowPointStatsFdTxFb                PerfCounter64,
    f3AccFlowPointStatsFdicd                 PerfCounter64,
    f3AccFlowPointStatsNumLearnTableFlushes  PerfCounter64
}

f3AccFlowPointStatsIndex OBJECT-TYPE
    SYNTAX      Integer32 (1..65535)
    MAX-ACCESS  read-only
    STATUS      current
    DESCRIPTION
            "An arbitrary integer index value used to uniquely identify
            this Access Ethernet Flowpoint statistics entry.
            Index 1 corresponds to 15minute, index 2 to 1 day and index
            3 corresponds to rollover."
    ::= { f3AccFlowPointStatsEntry 1 }

f3AccFlowPointStatsIntervalType OBJECT-TYPE
    SYNTAX      CmPmIntervalType
    MAX-ACCESS  read-only
    STATUS      current
    DESCRIPTION
            "Interval over which Performance Monitoring data is collected."
    ::= { f3AccFlowPointStatsEntry 2 }

f3AccFlowPointStatsValid OBJECT-TYPE
    SYNTAX      TruthValue
    MAX-ACCESS  read-only
    STATUS      current
    DESCRIPTION
            "Indicates the validity of the bin."
    ::= { f3AccFlowPointStatsEntry 3 }

f3AccFlowPointStatsAction OBJECT-TYPE
    SYNTAX      CmPmBinAction
    MAX-ACCESS  read-write
    STATUS      current
    DESCRIPTION
            "Allows the Manager to clear the bin."
    ::= { f3AccFlowPointStatsEntry 4 }

f3AccFlowPointStatsL2CPFD OBJECT-TYPE
     SYNTAX     PerfCounter64
     MAX-ACCESS read-only
     STATUS     current
     DESCRIPTION
         "Layer 2 Control Protocol Frames Discarded."
     ::= { f3AccFlowPointStatsEntry 5 }

f3AccFlowPointStatsABRRx OBJECT-TYPE
     SYNTAX     PerfCounter64
     MAX-ACCESS read-only
     STATUS     current
     DESCRIPTION
         "The average bit rate." 
     ::= { f3AccFlowPointStatsEntry 6 }

f3AccFlowPointStatsABRRLRx OBJECT-TYPE
     SYNTAX     PerfCounter64
     MAX-ACCESS read-only
     STATUS     current
     DESCRIPTION
         "The average bit rate, rate limited." 
     ::= { f3AccFlowPointStatsEntry 7 }

f3AccFlowPointStatsUAS OBJECT-TYPE
     SYNTAX     PerfCounter64
     MAX-ACCESS read-only
     STATUS     current
     DESCRIPTION
         "The number of Unavailable Seconds (UAS)."
     ::= { f3AccFlowPointStatsEntry 8 }

f3AccFlowPointStatsSES OBJECT-TYPE
     SYNTAX     PerfCounter64
     MAX-ACCESS read-only
     STATUS     current
     DESCRIPTION
         "The number of Severely Errored Seconds (ES)."
     ::= { f3AccFlowPointStatsEntry 9 }

f3AccFlowPointStatsFMG OBJECT-TYPE
     SYNTAX     PerfCounter64
     MAX-ACCESS read-only
     STATUS     current
     DESCRIPTION
         "The number of Frames Marked Green."
     ::= { f3AccFlowPointStatsEntry 10 }

f3AccFlowPointStatsFMY OBJECT-TYPE
     SYNTAX     PerfCounter64
     MAX-ACCESS read-only
     STATUS     current
     DESCRIPTION
         "The number of Frames Marked Yellow."
     ::= { f3AccFlowPointStatsEntry 11 }

f3AccFlowPointStatsFMRD OBJECT-TYPE
     SYNTAX     PerfCounter64
     MAX-ACCESS read-only
     STATUS     current
     DESCRIPTION
         "The number of Frames Marked Red and Discarded."
     ::= { f3AccFlowPointStatsEntry 12 }

f3AccFlowPointStatsFTD OBJECT-TYPE
     SYNTAX     PerfCounter64
     MAX-ACCESS read-only
     STATUS     current
     DESCRIPTION
         "The number of Frames Tail Dropped."
     ::= { f3AccFlowPointStatsEntry 13 }

f3AccFlowPointStatsBytesIn OBJECT-TYPE
     SYNTAX     PerfCounter64
     MAX-ACCESS read-only
     STATUS     current
     DESCRIPTION
         "The number of Bytes In in the ingress direction."
     ::= { f3AccFlowPointStatsEntry 14 }

f3AccFlowPointStatsBytesOut OBJECT-TYPE
     SYNTAX     PerfCounter64
     MAX-ACCESS read-only
     STATUS     current
     DESCRIPTION
         "The number of Bytes Out in the ingress direction."
     ::= { f3AccFlowPointStatsEntry 15 }
     
f3AccFlowPointStatsIBRMax OBJECT-TYPE
     SYNTAX     PerfCounter64
     MAX-ACCESS read-only
     STATUS     current
     DESCRIPTION
         "Instantaneous Bit Rate Maximum."
     ::= { f3AccFlowPointStatsEntry 16 }

f3AccFlowPointStatsIBRRlMax OBJECT-TYPE
     SYNTAX     PerfCounter64
     MAX-ACCESS read-only
     STATUS     current
     DESCRIPTION
         "Instantaneous Bit Rate Maximum - Rate Limited."
     ::= { f3AccFlowPointStatsEntry 17 }

f3AccFlowPointStatsIBRMin OBJECT-TYPE
     SYNTAX     PerfCounter64
     MAX-ACCESS read-only
     STATUS     current
     DESCRIPTION
         "Instantaneous Bit Rate Minimum."
     ::= { f3AccFlowPointStatsEntry 18 }

f3AccFlowPointStatsIBRRlMin OBJECT-TYPE
     SYNTAX     PerfCounter64
     MAX-ACCESS read-only
     STATUS     current
     DESCRIPTION
         "Instantaneous Bit Rate Minimum - Rate Limited."
     ::= { f3AccFlowPointStatsEntry 19 }

f3AccFlowPointStatsIBR OBJECT-TYPE
     SYNTAX     PerfCounter64
     MAX-ACCESS read-only
     STATUS     current
     DESCRIPTION
         "Instantaneous Bit Rate Minimum."
     ::= { f3AccFlowPointStatsEntry 20 }

f3AccFlowPointStatsIBRRl OBJECT-TYPE
     SYNTAX     PerfCounter64
     MAX-ACCESS read-only
     STATUS     current
     DESCRIPTION
         "Instantaneous Bit Rate Minimum - Rate Limited."
     ::= { f3AccFlowPointStatsEntry 21 }

f3AccFlowPointStatsFBCD OBJECT-TYPE
     SYNTAX     PerfCounter64
     MAX-ACCESS read-only
     STATUS     current
     DESCRIPTION
         "The number of Frames Dropped - Broadcast Rate Limit."
     ::= { f3AccFlowPointStatsEntry 22 }

f3AccFlowPointStatsFMCD OBJECT-TYPE
     SYNTAX     PerfCounter64
     MAX-ACCESS read-only
     STATUS     current
     DESCRIPTION
         "The number of Frames Dropped - Multicast Rate Limit."
     ::= { f3AccFlowPointStatsEntry 23 }

f3AccFlowPointStatsFdRxFb OBJECT-TYPE
     SYNTAX     PerfCounter64
     MAX-ACCESS read-only
     STATUS     current
     DESCRIPTION
         "The number of Frames Dropped RX - Flowpoint Blocked."
     ::= { f3AccFlowPointStatsEntry 24 }

f3AccFlowPointStatsFdTxFb OBJECT-TYPE
     SYNTAX     PerfCounter64
     MAX-ACCESS read-only
     STATUS     current
     DESCRIPTION
         "The number of Frames Dropped TX - Flowpoint Blocked."
     ::= { f3AccFlowPointStatsEntry 25 }

f3AccFlowPointStatsFdicd OBJECT-TYPE
     SYNTAX     PerfCounter64
     MAX-ACCESS read-only
     STATUS     current
     DESCRIPTION
         "The number of Frames Dropped - Ingress COS Disabled."
     ::= { f3AccFlowPointStatsEntry 26 }

f3AccFlowPointStatsNumLearnTableFlushes OBJECT-TYPE
     SYNTAX     PerfCounter64
     MAX-ACCESS read-only
     STATUS     current
     DESCRIPTION
         "The number of learning table flushes."
     ::= { f3AccFlowPointStatsEntry 27 }

--
-- Network Flowpoint Current Statistics Table
--

f3NetFlowPointStatsTable OBJECT-TYPE
    SYNTAX      SEQUENCE OF F3NetFlowPointStatsEntry
    MAX-ACCESS  not-accessible
    STATUS      current
    DESCRIPTION
            "A collection of FlowPoint statistics.  
             These reflect the current data."
    ::= { f3FpmPerfObjects 2 }

f3NetFlowPointStatsEntry OBJECT-TYPE
    SYNTAX      F3NetFlowPointStatsEntry 
    MAX-ACCESS  not-accessible
    STATUS      current
    DESCRIPTION
            "A conceptual row in the f3NetFlowPointStatsTable.
             Entries exist in this table for each FlowPoint."
    INDEX { neIndex, shelfIndex, slotIndex, cmEthernetNetPortIndex,
            f3NetFlowPointIndex, f3NetFlowPointStatsIndex }
    ::= { f3NetFlowPointStatsTable 1 }

F3NetFlowPointStatsEntry ::= SEQUENCE {
    f3NetFlowPointStatsIndex                 Integer32,
    f3NetFlowPointStatsIntervalType          CmPmIntervalType,
    f3NetFlowPointStatsValid                 TruthValue,
    f3NetFlowPointStatsAction                CmPmBinAction,
    f3NetFlowPointStatsL2CPFD                PerfCounter64,
    f3NetFlowPointStatsABRRx                 PerfCounter64,
    f3NetFlowPointStatsABRRLRx               PerfCounter64,
    f3NetFlowPointStatsUAS                   PerfCounter64,
    f3NetFlowPointStatsSES                   PerfCounter64, 
    f3NetFlowPointStatsFMG                   PerfCounter64,
    f3NetFlowPointStatsFMY                   PerfCounter64,
    f3NetFlowPointStatsFMRD                  PerfCounter64,
    f3NetFlowPointStatsFTD                   PerfCounter64,
    f3NetFlowPointStatsBytesIn               PerfCounter64,
    f3NetFlowPointStatsBytesOut              PerfCounter64,
    f3NetFlowPointStatsIBRMax                PerfCounter64,
    f3NetFlowPointStatsIBRRlMax              PerfCounter64,
    f3NetFlowPointStatsIBRMin                PerfCounter64,
    f3NetFlowPointStatsIBRRlMin              PerfCounter64,
    f3NetFlowPointStatsIBR                   PerfCounter64,
    f3NetFlowPointStatsIBRRl                 PerfCounter64,
    f3NetFlowPointStatsFBCD                  PerfCounter64,
    f3NetFlowPointStatsFMCD                  PerfCounter64,
    f3NetFlowPointStatsFdRxFb                PerfCounter64,
    f3NetFlowPointStatsFdTxFb                PerfCounter64,
    f3NetFlowPointStatsFdicd                 PerfCounter64,
    f3NetFlowPointStatsNumLearnTableFlushes  PerfCounter64
}

f3NetFlowPointStatsIndex OBJECT-TYPE
    SYNTAX      Integer32 (1..65535)
    MAX-ACCESS  read-only
    STATUS      current
    DESCRIPTION
            "An arbitrary integer index value used to uniquely identify
            this Access Ethernet Flowpoint statistics entry.
            Index 1 corresponds to 15minute, index 2 to 1 day and index
            3 corresponds to rollover."
    ::= { f3NetFlowPointStatsEntry 1 }

f3NetFlowPointStatsIntervalType OBJECT-TYPE
    SYNTAX      CmPmIntervalType
    MAX-ACCESS  read-only
    STATUS      current
    DESCRIPTION
            "Interval over which Performance Monitoring data is collected."
    ::= { f3NetFlowPointStatsEntry 2 }

f3NetFlowPointStatsValid OBJECT-TYPE
    SYNTAX      TruthValue
    MAX-ACCESS  read-only
    STATUS      current
    DESCRIPTION
            "Indicates the validity of the bin."
    ::= { f3NetFlowPointStatsEntry 3 }

f3NetFlowPointStatsAction OBJECT-TYPE
    SYNTAX      CmPmBinAction
    MAX-ACCESS  read-write
    STATUS      current
    DESCRIPTION
            "Allows the Manager to clear the bin."
    ::= { f3NetFlowPointStatsEntry 4 }

f3NetFlowPointStatsL2CPFD OBJECT-TYPE
     SYNTAX     PerfCounter64
     MAX-ACCESS read-only
     STATUS     current
     DESCRIPTION
         "Layer 2 Control Protocol Frames Discarded."
     ::= { f3NetFlowPointStatsEntry 5 }

f3NetFlowPointStatsABRRx OBJECT-TYPE
     SYNTAX     PerfCounter64
     MAX-ACCESS read-only
     STATUS     current
     DESCRIPTION
         "The average bit rate." 
     ::= { f3NetFlowPointStatsEntry 6 }

f3NetFlowPointStatsABRRLRx OBJECT-TYPE
     SYNTAX     PerfCounter64
     MAX-ACCESS read-only
     STATUS     current
     DESCRIPTION
         "The average bit rate, rate limited." 
     ::= { f3NetFlowPointStatsEntry 7 }

f3NetFlowPointStatsUAS OBJECT-TYPE
     SYNTAX     PerfCounter64
     MAX-ACCESS read-only
     STATUS     current
     DESCRIPTION
         "The number of Unavailable Seconds (UAS)."
     ::= { f3NetFlowPointStatsEntry 8 }

f3NetFlowPointStatsSES OBJECT-TYPE
     SYNTAX     PerfCounter64
     MAX-ACCESS read-only
     STATUS     current
     DESCRIPTION
         "The number of Severely Errored Seconds (ES)."
     ::= { f3NetFlowPointStatsEntry 9 }

f3NetFlowPointStatsFMG OBJECT-TYPE
     SYNTAX     PerfCounter64
     MAX-ACCESS read-only
     STATUS     current
     DESCRIPTION
         "The number of Frames Marked Green."
     ::= { f3NetFlowPointStatsEntry 10 }

f3NetFlowPointStatsFMY OBJECT-TYPE
     SYNTAX     PerfCounter64
     MAX-ACCESS read-only
     STATUS     current
     DESCRIPTION
         "The number of Frames Marked Yellow."
     ::= { f3NetFlowPointStatsEntry 11 }

f3NetFlowPointStatsFMRD OBJECT-TYPE
     SYNTAX     PerfCounter64
     MAX-ACCESS read-only
     STATUS     current
     DESCRIPTION
         "The number of Frames Marked Red and Discarded."
     ::= { f3NetFlowPointStatsEntry 12 }

f3NetFlowPointStatsFTD OBJECT-TYPE
     SYNTAX     PerfCounter64
     MAX-ACCESS read-only
     STATUS     current
     DESCRIPTION
         "The number of Frames Tail Dropped."
     ::= { f3NetFlowPointStatsEntry 13 }

f3NetFlowPointStatsBytesIn OBJECT-TYPE
     SYNTAX     PerfCounter64
     MAX-ACCESS read-only
     STATUS     current
     DESCRIPTION
         "The number of Bytes In in the ingress direction."
     ::= { f3NetFlowPointStatsEntry 14 }

f3NetFlowPointStatsBytesOut OBJECT-TYPE
     SYNTAX     PerfCounter64
     MAX-ACCESS read-only
     STATUS     current
     DESCRIPTION
         "The number of Bytes Out in the ingress direction."
     ::= { f3NetFlowPointStatsEntry 15 }
     
f3NetFlowPointStatsIBRMax OBJECT-TYPE
     SYNTAX     PerfCounter64
     MAX-ACCESS read-only
     STATUS     current
     DESCRIPTION
         "Instantaneous Bit Rate Maximum."
     ::= { f3NetFlowPointStatsEntry 16 }

f3NetFlowPointStatsIBRRlMax OBJECT-TYPE
     SYNTAX     PerfCounter64
     MAX-ACCESS read-only
     STATUS     current
     DESCRIPTION
         "Instantaneous Bit Rate Maximum - Rate Limited."
     ::= { f3NetFlowPointStatsEntry 17 }

f3NetFlowPointStatsIBRMin OBJECT-TYPE
     SYNTAX     PerfCounter64
     MAX-ACCESS read-only
     STATUS     current
     DESCRIPTION
         "Instantaneous Bit Rate Minimum."
     ::= { f3NetFlowPointStatsEntry 18 }

f3NetFlowPointStatsIBRRlMin OBJECT-TYPE
     SYNTAX     PerfCounter64
     MAX-ACCESS read-only
     STATUS     current
     DESCRIPTION
         "Instantaneous Bit Rate Minimum - Rate Limited."
     ::= { f3NetFlowPointStatsEntry 19 }

f3NetFlowPointStatsIBR OBJECT-TYPE
     SYNTAX     PerfCounter64
     MAX-ACCESS read-only
     STATUS     current
     DESCRIPTION
         "Instantaneous Bit Rate Minimum."
     ::= { f3NetFlowPointStatsEntry 20 }

f3NetFlowPointStatsIBRRl OBJECT-TYPE
     SYNTAX     PerfCounter64
     MAX-ACCESS read-only
     STATUS     current
     DESCRIPTION
         "Instantaneous Bit Rate Minimum - Rate Limited."
     ::= { f3NetFlowPointStatsEntry 21 }

f3NetFlowPointStatsFBCD OBJECT-TYPE
     SYNTAX     PerfCounter64
     MAX-ACCESS read-only
     STATUS     current
     DESCRIPTION
         "The number of Frames Dropped - Broadcast Rate Limit."
     ::= { f3NetFlowPointStatsEntry 22 }

f3NetFlowPointStatsFMCD OBJECT-TYPE
     SYNTAX     PerfCounter64
     MAX-ACCESS read-only
     STATUS     current
     DESCRIPTION
         "The number of Frames Dropped - Multicast Rate Limit."
     ::= { f3NetFlowPointStatsEntry 23 }

f3NetFlowPointStatsFdRxFb OBJECT-TYPE
     SYNTAX     PerfCounter64
     MAX-ACCESS read-only
     STATUS     current
     DESCRIPTION
         "The number of Frames Dropped RX - Flowpoint Blocked."
     ::= { f3NetFlowPointStatsEntry 24 }

f3NetFlowPointStatsFdTxFb OBJECT-TYPE
     SYNTAX     PerfCounter64
     MAX-ACCESS read-only
     STATUS     current
     DESCRIPTION
         "The number of Frames Dropped TX - Flowpoint Blocked."
     ::= { f3NetFlowPointStatsEntry 25 }

f3NetFlowPointStatsFdicd OBJECT-TYPE
     SYNTAX     PerfCounter64
     MAX-ACCESS read-only
     STATUS     current
     DESCRIPTION
         "The number of Frames Dropped - Ingress COS Disabled."
     ::= { f3NetFlowPointStatsEntry 26 }

f3NetFlowPointStatsNumLearnTableFlushes OBJECT-TYPE
     SYNTAX     PerfCounter64
     MAX-ACCESS read-only
     STATUS     current
     DESCRIPTION
         "The number of learning table flushes."
     ::= { f3NetFlowPointStatsEntry 27 }

--
-- Access Flowpoint History Statistics Table
--

f3AccFlowPointHistoryTable OBJECT-TYPE
    SYNTAX      SEQUENCE OF F3AccFlowPointHistoryEntry
    MAX-ACCESS  not-accessible
    STATUS      current
    DESCRIPTION
            "A collection of FlowPoint statistics.  
             These reflect the history data."
    ::= { f3FpmPerfObjects 3 }

f3AccFlowPointHistoryEntry OBJECT-TYPE
    SYNTAX      F3AccFlowPointHistoryEntry 
    MAX-ACCESS  not-accessible
    STATUS      current
    DESCRIPTION
            "A conceptual row in the f3AccFlowPointHistoryTable.
             Entries exist in this table for each FlowPoint."
    INDEX { neIndex, shelfIndex, slotIndex, cmEthernetAccPortIndex,
            f3AccFlowPointIndex, f3AccFlowPointStatsIndex, 
            f3AccFlowPointHistoryIndex }
    ::= { f3AccFlowPointHistoryTable 1 }

F3AccFlowPointHistoryEntry ::= SEQUENCE {
    f3AccFlowPointHistoryIndex                 Integer32,
    f3AccFlowPointHistoryTime                  DateAndTime,
    f3AccFlowPointHistoryValid                 TruthValue,
    f3AccFlowPointHistoryAction                CmPmBinAction,
    f3AccFlowPointHistoryL2CPFD                PerfCounter64,
    f3AccFlowPointHistoryABRRx                 PerfCounter64,
    f3AccFlowPointHistoryABRRLRx               PerfCounter64,
    f3AccFlowPointHistoryUAS                   PerfCounter64,
    f3AccFlowPointHistorySES                   PerfCounter64, 
    f3AccFlowPointHistoryFMG                   PerfCounter64,
    f3AccFlowPointHistoryFMY                   PerfCounter64,
    f3AccFlowPointHistoryFMRD                  PerfCounter64,
    f3AccFlowPointHistoryFTD                   PerfCounter64,
    f3AccFlowPointHistoryBytesIn               PerfCounter64,
    f3AccFlowPointHistoryBytesOut              PerfCounter64,
    f3AccFlowPointHistoryIBRMax                PerfCounter64,
    f3AccFlowPointHistoryIBRRlMax              PerfCounter64,
    f3AccFlowPointHistoryIBRMin                PerfCounter64,
    f3AccFlowPointHistoryIBRRlMin              PerfCounter64,
    f3AccFlowPointHistoryIBR                   PerfCounter64,
    f3AccFlowPointHistoryIBRRl                 PerfCounter64,
    f3AccFlowPointHistoryFBCD                  PerfCounter64,
    f3AccFlowPointHistoryFMCD                  PerfCounter64,
    f3AccFlowPointHistoryFdRxFb                PerfCounter64,
    f3AccFlowPointHistoryFdTxFb                PerfCounter64,
    f3AccFlowPointHistoryFdicd                 PerfCounter64,
    f3AccFlowPointHistoryNumLearnTableFlushes  PerfCounter64
}

f3AccFlowPointHistoryIndex OBJECT-TYPE
    SYNTAX      Integer32 (1..65535)
    MAX-ACCESS  read-only
    STATUS      current
    DESCRIPTION
            "An arbitrary integer index value used to uniquely identify
            this Access Ethernet Flowpoint History statistics entry.
            Index 1 corresponds to 15minute, index 2 to 1 day and index
            3 corresponds to rollover."
    ::= { f3AccFlowPointHistoryEntry 1 }

f3AccFlowPointHistoryTime OBJECT-TYPE
    SYNTAX      DateAndTime
    MAX-ACCESS  read-only
    STATUS      current
    DESCRIPTION
            "Indicates the time of history bin creation."
    ::= { f3AccFlowPointHistoryEntry 2 }

f3AccFlowPointHistoryValid OBJECT-TYPE
    SYNTAX      TruthValue
    MAX-ACCESS  read-only
    STATUS      current
    DESCRIPTION
            "Indicates the validity of the bin."
    ::= { f3AccFlowPointHistoryEntry 3 }

f3AccFlowPointHistoryAction OBJECT-TYPE
    SYNTAX      CmPmBinAction
    MAX-ACCESS  read-write
    STATUS      current
    DESCRIPTION
            "Allows the Manager to clear the bin."
    ::= { f3AccFlowPointHistoryEntry 4 }

f3AccFlowPointHistoryL2CPFD OBJECT-TYPE
     SYNTAX     PerfCounter64
     MAX-ACCESS read-only
     STATUS     current
     DESCRIPTION
         "Layer 2 Control Protocol Frames Discarded."
     ::= { f3AccFlowPointHistoryEntry 5 }

f3AccFlowPointHistoryABRRx OBJECT-TYPE
     SYNTAX     PerfCounter64
     MAX-ACCESS read-only
     STATUS     current
     DESCRIPTION
         "The average bit rate." 
     ::= { f3AccFlowPointHistoryEntry 6 }

f3AccFlowPointHistoryABRRLRx OBJECT-TYPE
     SYNTAX     PerfCounter64
     MAX-ACCESS read-only
     STATUS     current
     DESCRIPTION
         "The average bit rate, rate limited." 
     ::= { f3AccFlowPointHistoryEntry 7 }

f3AccFlowPointHistoryUAS OBJECT-TYPE
     SYNTAX     PerfCounter64
     MAX-ACCESS read-only
     STATUS     current
     DESCRIPTION
         "The number of Unavailable Seconds (UAS)."
     ::= { f3AccFlowPointHistoryEntry 8 }

f3AccFlowPointHistorySES OBJECT-TYPE
     SYNTAX     PerfCounter64
     MAX-ACCESS read-only
     STATUS     current
     DESCRIPTION
         "The number of Severely Errored Seconds (ES)."
     ::= { f3AccFlowPointHistoryEntry 9 }

f3AccFlowPointHistoryFMG OBJECT-TYPE
     SYNTAX     PerfCounter64
     MAX-ACCESS read-only
     STATUS     current
     DESCRIPTION
         "The number of Frames Marked Green."
     ::= { f3AccFlowPointHistoryEntry 10 }

f3AccFlowPointHistoryFMY OBJECT-TYPE
     SYNTAX     PerfCounter64
     MAX-ACCESS read-only
     STATUS     current
     DESCRIPTION
         "The number of Frames Marked Yellow."
     ::= { f3AccFlowPointHistoryEntry 11 }

f3AccFlowPointHistoryFMRD OBJECT-TYPE
     SYNTAX     PerfCounter64
     MAX-ACCESS read-only
     STATUS     current
     DESCRIPTION
         "The number of Frames Marked Red and Discarded."
     ::= { f3AccFlowPointHistoryEntry 12 }

f3AccFlowPointHistoryFTD OBJECT-TYPE
     SYNTAX     PerfCounter64
     MAX-ACCESS read-only
     STATUS     current
     DESCRIPTION
         "The number of Frames Tail Dropped."
     ::= { f3AccFlowPointHistoryEntry 13 }

f3AccFlowPointHistoryBytesIn OBJECT-TYPE
     SYNTAX     PerfCounter64
     MAX-ACCESS read-only
     STATUS     current
     DESCRIPTION
         "The number of Bytes In in the ingress direction."
     ::= { f3AccFlowPointHistoryEntry 14 }

f3AccFlowPointHistoryBytesOut OBJECT-TYPE
     SYNTAX     PerfCounter64
     MAX-ACCESS read-only
     STATUS     current
     DESCRIPTION
         "The number of Bytes Out in the ingress direction."
     ::= { f3AccFlowPointHistoryEntry 15 }
     
f3AccFlowPointHistoryIBRMax OBJECT-TYPE
     SYNTAX     PerfCounter64
     MAX-ACCESS read-only
     STATUS     current
     DESCRIPTION
         "Instantaneous Bit Rate Maximum."
     ::= { f3AccFlowPointHistoryEntry 16 }

f3AccFlowPointHistoryIBRRlMax OBJECT-TYPE
     SYNTAX     PerfCounter64
     MAX-ACCESS read-only
     STATUS     current
     DESCRIPTION
         "Instantaneous Bit Rate Maximum - Rate Limited."
     ::= { f3AccFlowPointHistoryEntry 17 }

f3AccFlowPointHistoryIBRMin OBJECT-TYPE
     SYNTAX     PerfCounter64
     MAX-ACCESS read-only
     STATUS     current
     DESCRIPTION
         "Instantaneous Bit Rate Minimum."
     ::= { f3AccFlowPointHistoryEntry 18 }

f3AccFlowPointHistoryIBRRlMin OBJECT-TYPE
     SYNTAX     PerfCounter64
     MAX-ACCESS read-only
     STATUS     current
     DESCRIPTION
         "Instantaneous Bit Rate Minimum - Rate Limited."
     ::= { f3AccFlowPointHistoryEntry 19 }

f3AccFlowPointHistoryIBR OBJECT-TYPE
     SYNTAX     PerfCounter64
     MAX-ACCESS read-only
     STATUS     current
     DESCRIPTION
         "Instantaneous Bit Rate Minimum."
     ::= { f3AccFlowPointHistoryEntry 20 }

f3AccFlowPointHistoryIBRRl OBJECT-TYPE
     SYNTAX     PerfCounter64
     MAX-ACCESS read-only
     STATUS     current
     DESCRIPTION
         "Instantaneous Bit Rate Minimum - Rate Limited."
     ::= { f3AccFlowPointHistoryEntry 21 }

f3AccFlowPointHistoryFBCD OBJECT-TYPE
     SYNTAX     PerfCounter64
     MAX-ACCESS read-only
     STATUS     current
     DESCRIPTION
         "The number of Frames Dropped - Broadcast Rate Limit."
     ::= { f3AccFlowPointHistoryEntry 22 }

f3AccFlowPointHistoryFMCD OBJECT-TYPE
     SYNTAX     PerfCounter64
     MAX-ACCESS read-only
     STATUS     current
     DESCRIPTION
         "The number of Frames Dropped - Multicast Rate Limit."
     ::= { f3AccFlowPointHistoryEntry 23 }

f3AccFlowPointHistoryFdRxFb OBJECT-TYPE
     SYNTAX     PerfCounter64
     MAX-ACCESS read-only
     STATUS     current
     DESCRIPTION
         "The number of Frames Dropped RX - Flowpoint Blocked."
     ::= { f3AccFlowPointHistoryEntry 24 }

f3AccFlowPointHistoryFdTxFb OBJECT-TYPE
     SYNTAX     PerfCounter64
     MAX-ACCESS read-only
     STATUS     current
     DESCRIPTION
         "The number of Frames Dropped TX - Flowpoint Blocked."
     ::= { f3AccFlowPointHistoryEntry 25 }

f3AccFlowPointHistoryFdicd OBJECT-TYPE
     SYNTAX     PerfCounter64
     MAX-ACCESS read-only
     STATUS     current
     DESCRIPTION
         "The number of Frames Dropped - Ingress COS Disabled."
     ::= { f3AccFlowPointHistoryEntry 26 }

f3AccFlowPointHistoryNumLearnTableFlushes OBJECT-TYPE
     SYNTAX     PerfCounter64
     MAX-ACCESS read-only
     STATUS     current
     DESCRIPTION
         "The number of learning table flushes."
     ::= { f3AccFlowPointHistoryEntry 27 }

--
-- Network Flowpoint History Statistics Table
--

f3NetFlowPointHistoryTable OBJECT-TYPE
    SYNTAX      SEQUENCE OF F3NetFlowPointHistoryEntry
    MAX-ACCESS  not-accessible
    STATUS      current
    DESCRIPTION
            "A collection of FlowPoint statistics.  
             These reflect the history data."
    ::= { f3FpmPerfObjects 4 }

f3NetFlowPointHistoryEntry OBJECT-TYPE
    SYNTAX      F3NetFlowPointHistoryEntry 
    MAX-ACCESS  not-accessible
    STATUS      current
    DESCRIPTION
            "A conceptual row in the f3NetFlowPointHistoryTable.
             Entries exist in this table for each FlowPoint."
    INDEX { neIndex, shelfIndex, slotIndex, cmEthernetNetPortIndex,
            f3NetFlowPointIndex, f3NetFlowPointStatsIndex, 
            f3NetFlowPointHistoryIndex }
    ::= { f3NetFlowPointHistoryTable 1 }

F3NetFlowPointHistoryEntry ::= SEQUENCE {
    f3NetFlowPointHistoryIndex                 Integer32,
    f3NetFlowPointHistoryTime                  DateAndTime,
    f3NetFlowPointHistoryValid                 TruthValue,
    f3NetFlowPointHistoryAction                CmPmBinAction,
    f3NetFlowPointHistoryL2CPFD                PerfCounter64,
    f3NetFlowPointHistoryABRRx                 PerfCounter64,
    f3NetFlowPointHistoryABRRLRx               PerfCounter64,
    f3NetFlowPointHistoryUAS                   PerfCounter64,
    f3NetFlowPointHistorySES                   PerfCounter64, 
    f3NetFlowPointHistoryFMG                   PerfCounter64,
    f3NetFlowPointHistoryFMY                   PerfCounter64,
    f3NetFlowPointHistoryFMRD                  PerfCounter64,
    f3NetFlowPointHistoryFTD                   PerfCounter64,
    f3NetFlowPointHistoryBytesIn               PerfCounter64,
    f3NetFlowPointHistoryBytesOut              PerfCounter64,
    f3NetFlowPointHistoryIBRMax                PerfCounter64,
    f3NetFlowPointHistoryIBRRlMax              PerfCounter64,
    f3NetFlowPointHistoryIBRMin                PerfCounter64,
    f3NetFlowPointHistoryIBRRlMin              PerfCounter64,
    f3NetFlowPointHistoryIBR                   PerfCounter64,
    f3NetFlowPointHistoryIBRRl                 PerfCounter64,
    f3NetFlowPointHistoryFBCD                  PerfCounter64,
    f3NetFlowPointHistoryFMCD                  PerfCounter64,
    f3NetFlowPointHistoryFdRxFb                PerfCounter64,
    f3NetFlowPointHistoryFdTxFb                PerfCounter64,
    f3NetFlowPointHistoryFdicd                 PerfCounter64,
    f3NetFlowPointHistoryNumLearnTableFlushes  PerfCounter64
}

f3NetFlowPointHistoryIndex OBJECT-TYPE
    SYNTAX      Integer32 (1..65535)
    MAX-ACCESS  read-only
    STATUS      current
    DESCRIPTION
            "An arbitrary integer index value used to uniquely identify
            this Access Ethernet Flowpoint History statistics entry.
            Index 1 corresponds to 15minute, index 2 to 1 day and index
            3 corresponds to rollover."
    ::= { f3NetFlowPointHistoryEntry 1 }

f3NetFlowPointHistoryTime OBJECT-TYPE
    SYNTAX      DateAndTime
    MAX-ACCESS  read-only
    STATUS      current
    DESCRIPTION
            "Indicates the time of history bin creation."
    ::= { f3NetFlowPointHistoryEntry 2 }

f3NetFlowPointHistoryValid OBJECT-TYPE
    SYNTAX      TruthValue
    MAX-ACCESS  read-only
    STATUS      current
    DESCRIPTION
            "Indicates the validity of the bin."
    ::= { f3NetFlowPointHistoryEntry 3 }

f3NetFlowPointHistoryAction OBJECT-TYPE
    SYNTAX      CmPmBinAction
    MAX-ACCESS  read-write
    STATUS      current
    DESCRIPTION
            "Allows the Manager to clear the bin."
    ::= { f3NetFlowPointHistoryEntry 4 }

f3NetFlowPointHistoryL2CPFD OBJECT-TYPE
     SYNTAX     PerfCounter64
     MAX-ACCESS read-only
     STATUS     current
     DESCRIPTION
         "Layer 2 Control Protocol Frames Discarded."
     ::= { f3NetFlowPointHistoryEntry 5 }

f3NetFlowPointHistoryABRRx OBJECT-TYPE
     SYNTAX     PerfCounter64
     MAX-ACCESS read-only
     STATUS     current
     DESCRIPTION
         "The average bit rate." 
     ::= { f3NetFlowPointHistoryEntry 6 }

f3NetFlowPointHistoryABRRLRx OBJECT-TYPE
     SYNTAX     PerfCounter64
     MAX-ACCESS read-only
     STATUS     current
     DESCRIPTION
         "The average bit rate, rate limited." 
     ::= { f3NetFlowPointHistoryEntry 7 }

f3NetFlowPointHistoryUAS OBJECT-TYPE
     SYNTAX     PerfCounter64
     MAX-ACCESS read-only
     STATUS     current
     DESCRIPTION
         "The number of Unavailable Seconds (UAS)."
     ::= { f3NetFlowPointHistoryEntry 8 }

f3NetFlowPointHistorySES OBJECT-TYPE
     SYNTAX     PerfCounter64
     MAX-ACCESS read-only
     STATUS     current
     DESCRIPTION
         "The number of Severely Errored Seconds (ES)."
     ::= { f3NetFlowPointHistoryEntry 9 }

f3NetFlowPointHistoryFMG OBJECT-TYPE
     SYNTAX     PerfCounter64
     MAX-ACCESS read-only
     STATUS     current
     DESCRIPTION
         "The number of Frames Marked Green."
     ::= { f3NetFlowPointHistoryEntry 10 }

f3NetFlowPointHistoryFMY OBJECT-TYPE
     SYNTAX     PerfCounter64
     MAX-ACCESS read-only
     STATUS     current
     DESCRIPTION
         "The number of Frames Marked Yellow."
     ::= { f3NetFlowPointHistoryEntry 11 }

f3NetFlowPointHistoryFMRD OBJECT-TYPE
     SYNTAX     PerfCounter64
     MAX-ACCESS read-only
     STATUS     current
     DESCRIPTION
         "The number of Frames Marked Red and Discarded."
     ::= { f3NetFlowPointHistoryEntry 12 }

f3NetFlowPointHistoryFTD OBJECT-TYPE
     SYNTAX     PerfCounter64
     MAX-ACCESS read-only
     STATUS     current
     DESCRIPTION
         "The number of Frames Tail Dropped."
     ::= { f3NetFlowPointHistoryEntry 13 }

f3NetFlowPointHistoryBytesIn OBJECT-TYPE
     SYNTAX     PerfCounter64
     MAX-ACCESS read-only
     STATUS     current
     DESCRIPTION
         "The number of Bytes In in the ingress direction."
     ::= { f3NetFlowPointHistoryEntry 14 }

f3NetFlowPointHistoryBytesOut OBJECT-TYPE
     SYNTAX     PerfCounter64
     MAX-ACCESS read-only
     STATUS     current
     DESCRIPTION
         "The number of Bytes Out in the ingress direction."
     ::= { f3NetFlowPointHistoryEntry 15 }
     
f3NetFlowPointHistoryIBRMax OBJECT-TYPE
     SYNTAX     PerfCounter64
     MAX-ACCESS read-only
     STATUS     current
     DESCRIPTION
         "Instantaneous Bit Rate Maximum."
     ::= { f3NetFlowPointHistoryEntry 16 }

f3NetFlowPointHistoryIBRRlMax OBJECT-TYPE
     SYNTAX     PerfCounter64
     MAX-ACCESS read-only
     STATUS     current
     DESCRIPTION
         "Instantaneous Bit Rate Maximum - Rate Limited."
     ::= { f3NetFlowPointHistoryEntry 17 }

f3NetFlowPointHistoryIBRMin OBJECT-TYPE
     SYNTAX     PerfCounter64
     MAX-ACCESS read-only
     STATUS     current
     DESCRIPTION
         "Instantaneous Bit Rate Minimum."
     ::= { f3NetFlowPointHistoryEntry 18 }

f3NetFlowPointHistoryIBRRlMin OBJECT-TYPE
     SYNTAX     PerfCounter64
     MAX-ACCESS read-only
     STATUS     current
     DESCRIPTION
         "Instantaneous Bit Rate Minimum - Rate Limited."
     ::= { f3NetFlowPointHistoryEntry 19 }

f3NetFlowPointHistoryIBR OBJECT-TYPE
     SYNTAX     PerfCounter64
     MAX-ACCESS read-only
     STATUS     current
     DESCRIPTION
         "Instantaneous Bit Rate Minimum."
     ::= { f3NetFlowPointHistoryEntry 20 }

f3NetFlowPointHistoryIBRRl OBJECT-TYPE
     SYNTAX     PerfCounter64
     MAX-ACCESS read-only
     STATUS     current
     DESCRIPTION
         "Instantaneous Bit Rate Minimum - Rate Limited."
     ::= { f3NetFlowPointHistoryEntry 21 }

f3NetFlowPointHistoryFBCD OBJECT-TYPE
     SYNTAX     PerfCounter64
     MAX-ACCESS read-only
     STATUS     current
     DESCRIPTION
         "The number of Frames Dropped - Broadcast Rate Limit."
     ::= { f3NetFlowPointHistoryEntry 22 }

f3NetFlowPointHistoryFMCD OBJECT-TYPE
     SYNTAX     PerfCounter64
     MAX-ACCESS read-only
     STATUS     current
     DESCRIPTION
         "The number of Frames Dropped - Multicast Rate Limit."
     ::= { f3NetFlowPointHistoryEntry 23 }

f3NetFlowPointHistoryFdRxFb OBJECT-TYPE
     SYNTAX     PerfCounter64
     MAX-ACCESS read-only
     STATUS     current
     DESCRIPTION
         "The number of Frames Dropped RX - Flowpoint Blocked."
     ::= { f3NetFlowPointHistoryEntry 24 }

f3NetFlowPointHistoryFdTxFb OBJECT-TYPE
     SYNTAX     PerfCounter64
     MAX-ACCESS read-only
     STATUS     current
     DESCRIPTION
         "The number of Frames Dropped TX - Flowpoint Blocked."
     ::= { f3NetFlowPointHistoryEntry 25 }

f3NetFlowPointHistoryFdicd OBJECT-TYPE
     SYNTAX     PerfCounter64
     MAX-ACCESS read-only
     STATUS     current
     DESCRIPTION
         "The number of Frames Dropped - Ingress COS Disabled."
     ::= { f3NetFlowPointHistoryEntry 26 }

f3NetFlowPointHistoryNumLearnTableFlushes OBJECT-TYPE
     SYNTAX     PerfCounter64
     MAX-ACCESS read-only
     STATUS     current
     DESCRIPTION
         "The number of learning table flushes."
     ::= { f3NetFlowPointHistoryEntry 27 }

--
-- Access FlowPoint Threshold Table
--

f3AccFlowPointThresholdTable OBJECT-TYPE
    SYNTAX      SEQUENCE OF F3AccFlowPointThresholdEntry
    MAX-ACCESS  not-accessible
    STATUS      current
    DESCRIPTION
            "A table of entries that allow manageability of Agg FlowPoint Thresholds."
    ::= { f3FpmPerfObjects 5 }

f3AccFlowPointThresholdEntry OBJECT-TYPE
    SYNTAX      F3AccFlowPointThresholdEntry
    MAX-ACCESS  not-accessible
    STATUS      current
    DESCRIPTION
            "A conceptual row in the f3AccFlowPointThresholdTable."
    INDEX { neIndex, shelfIndex, slotIndex, cmEthernetAccPortIndex, 
            f3AccFlowPointIndex, f3AccFlowPointStatsIndex, f3AccFlowPointThresholdIndex }
    ::= { f3AccFlowPointThresholdTable 1 }

F3AccFlowPointThresholdEntry ::= SEQUENCE {
    f3AccFlowPointThresholdIndex       Integer32,
    f3AccFlowPointThresholdInterval    CmPmIntervalType,
    f3AccFlowPointThresholdVariable    VariablePointer,
    f3AccFlowPointThresholdValueLo     Unsigned32,
    f3AccFlowPointThresholdValueHi     Unsigned32,
    f3AccFlowPointThresholdMonValue    Counter64
}

f3AccFlowPointThresholdIndex OBJECT-TYPE
    SYNTAX     Integer32 (1..65535)
    MAX-ACCESS read-only
    STATUS     current
    DESCRIPTION
        "An index that uniquely identifies an entry in the
         f3AccFlowPointThresholdTable."
    ::= { f3AccFlowPointThresholdEntry 1 }

f3AccFlowPointThresholdInterval OBJECT-TYPE
    SYNTAX     CmPmIntervalType
    MAX-ACCESS read-only
    STATUS     current
    DESCRIPTION
        "The interval over which monitored value is
         sampled and compared with the specified threshold."
    ::= { f3AccFlowPointThresholdEntry 2 }

f3AccFlowPointThresholdVariable OBJECT-TYPE
    SYNTAX     VariablePointer
    MAX-ACCESS read-only
    STATUS     current
    DESCRIPTION
        "The object identifier of the particular variable to be sampled."
    ::= { f3AccFlowPointThresholdEntry 3 }

f3AccFlowPointThresholdValueLo OBJECT-TYPE
    SYNTAX     Unsigned32
    MAX-ACCESS read-write
    STATUS     current
    DESCRIPTION
        "Lower 32 bits of the threshold value."
    ::= { f3AccFlowPointThresholdEntry 4 }

f3AccFlowPointThresholdValueHi OBJECT-TYPE
    SYNTAX     Unsigned32
    MAX-ACCESS read-write
    STATUS     current
    DESCRIPTION
        "Higher 32 bits of the threshold value."
    ::= { f3AccFlowPointThresholdEntry 5 }

f3AccFlowPointThresholdMonValue OBJECT-TYPE
    SYNTAX     Counter64
    MAX-ACCESS read-only
    STATUS     current
    DESCRIPTION
        "Monitored value corresponding to f3AccFlowPointThresholdVariable."
    ::= { f3AccFlowPointThresholdEntry 6 }

--
-- Network FlowPoint Threshold Table
--

f3NetFlowPointThresholdTable OBJECT-TYPE
    SYNTAX      SEQUENCE OF F3NetFlowPointThresholdEntry
    MAX-ACCESS  not-accessible
    STATUS      current
    DESCRIPTION
            "A table of entries that allow manageability of Agg FlowPoint Thresholds."
    ::= { f3FpmPerfObjects 6 }

f3NetFlowPointThresholdEntry OBJECT-TYPE
    SYNTAX      F3NetFlowPointThresholdEntry
    MAX-ACCESS  not-accessible
    STATUS      current
    DESCRIPTION
            "A conceptual row in the f3NetFlowPointThresholdTable."
    INDEX { neIndex, shelfIndex, slotIndex, cmEthernetNetPortIndex, 
            f3NetFlowPointIndex, f3NetFlowPointStatsIndex, f3NetFlowPointThresholdIndex }
    ::= { f3NetFlowPointThresholdTable 1 }

F3NetFlowPointThresholdEntry ::= SEQUENCE {
    f3NetFlowPointThresholdIndex       Integer32,
    f3NetFlowPointThresholdInterval    CmPmIntervalType,
    f3NetFlowPointThresholdVariable    VariablePointer,
    f3NetFlowPointThresholdValueLo     Unsigned32,
    f3NetFlowPointThresholdValueHi     Unsigned32,
    f3NetFlowPointThresholdMonValue    Counter64
}

f3NetFlowPointThresholdIndex OBJECT-TYPE
    SYNTAX     Integer32 (1..65535)
    MAX-ACCESS read-only
    STATUS     current
    DESCRIPTION
        "An index that uniquely identifies an entry in the
         f3NetFlowPointThresholdTable."
    ::= { f3NetFlowPointThresholdEntry 1 }

f3NetFlowPointThresholdInterval OBJECT-TYPE
    SYNTAX     CmPmIntervalType
    MAX-ACCESS read-only
    STATUS     current
    DESCRIPTION
        "The interval over which monitored value is
         sampled and compared with the specified threshold."
    ::= { f3NetFlowPointThresholdEntry 2 }

f3NetFlowPointThresholdVariable OBJECT-TYPE
    SYNTAX     VariablePointer
    MAX-ACCESS read-only
    STATUS     current
    DESCRIPTION
        "The object identifier of the particular variable to be sampled."
    ::= { f3NetFlowPointThresholdEntry 3 }

f3NetFlowPointThresholdValueLo OBJECT-TYPE
    SYNTAX     Unsigned32
    MAX-ACCESS read-write
    STATUS     current
    DESCRIPTION
        "Lower 32 bits of the threshold value."
    ::= { f3NetFlowPointThresholdEntry 4 }

f3NetFlowPointThresholdValueHi OBJECT-TYPE
    SYNTAX     Unsigned32
    MAX-ACCESS read-write
    STATUS     current
    DESCRIPTION
        "Higher 32 bits of the threshold value."
    ::= { f3NetFlowPointThresholdEntry 5 }

f3NetFlowPointThresholdMonValue OBJECT-TYPE
    SYNTAX     Counter64
    MAX-ACCESS read-only
    STATUS     current
    DESCRIPTION
        "Monitored value corresponding to f3NetFlowPointThresholdVariable."
    ::= { f3NetFlowPointThresholdEntry 6 }

--
-- MP Flow Current Statistics Table
--

f3MPFlowStatsTable OBJECT-TYPE
    SYNTAX      SEQUENCE OF F3MPFlowStatsEntry
    MAX-ACCESS  not-accessible
    STATUS      current
    DESCRIPTION
            "A collection of MP Flow statistics.  
             These reflect the current data."
    ::= { f3FpmPerfObjects 7 }

f3MPFlowStatsEntry OBJECT-TYPE
    SYNTAX      F3MPFlowStatsEntry 
    MAX-ACCESS  not-accessible
    STATUS      current
    DESCRIPTION
            "A conceptual row in the f3MPFlowStatsTable.
             Entries exist in this table for each MP Flow."
    INDEX { neIndex, cmMPFlowIndex, f3MPFlowStatsIndex }
    ::= { f3MPFlowStatsTable 1 }

F3MPFlowStatsEntry ::= SEQUENCE {
    f3MPFlowStatsIndex                 Integer32,
    f3MPFlowStatsIntervalType          CmPmIntervalType,
    f3MPFlowStatsValid                 TruthValue,
    f3MPFlowStatsAction                CmPmBinAction,
    f3MPFlowStatsFDStaticBlock         PerfCounter64,
    f3MPFlowStatsFDHairPin             PerfCounter64,
    f3MPFlowStatsMacTableDiscards      PerfCounter64, 
    f3MPFlowStatsFDProtLearn           PerfCounter64
}

f3MPFlowStatsIndex OBJECT-TYPE
    SYNTAX      Integer32 (1..65535)
    MAX-ACCESS  read-only
    STATUS      current
    DESCRIPTION
            "An arbitrary integer index value used to uniquely identify
             this MP Flow statistics entry. Index 1 corresponds to 15minute, 
             index 2 to 1 day and index 3 corresponds to rollover."
    ::= { f3MPFlowStatsEntry 1 }

f3MPFlowStatsIntervalType OBJECT-TYPE
    SYNTAX      CmPmIntervalType
    MAX-ACCESS  read-only
    STATUS      current
    DESCRIPTION
            "Interval over which Performance Monitoring data is collected."
    ::= { f3MPFlowStatsEntry 2 }

f3MPFlowStatsValid OBJECT-TYPE
    SYNTAX      TruthValue
    MAX-ACCESS  read-only
    STATUS      current
    DESCRIPTION
            "Indicates the validity of the bin."
    ::= { f3MPFlowStatsEntry 3 }

f3MPFlowStatsAction OBJECT-TYPE
    SYNTAX      CmPmBinAction
    MAX-ACCESS  read-write
    STATUS      current
    DESCRIPTION
            "Allows the Manager to clear the bin."
    ::= { f3MPFlowStatsEntry 4 }

f3MPFlowStatsFDStaticBlock OBJECT-TYPE
     SYNTAX     PerfCounter64
     MAX-ACCESS read-only
     STATUS     current
     DESCRIPTION
         "Specifies current counter for number of frames discarded due to a 
          static entry in Mac Table." 
     ::= { f3MPFlowStatsEntry 5 }

f3MPFlowStatsFDHairPin OBJECT-TYPE
     SYNTAX     PerfCounter64
     MAX-ACCESS read-only
     STATUS     current
     DESCRIPTION
         "Specifies current counter for number of frames discarded because 
          destination Port is the ingress flowpoint or destination Port is in the 
          same Split Horizon Group." 
     ::= { f3MPFlowStatsEntry 6 }

f3MPFlowStatsMacTableDiscards OBJECT-TYPE
     SYNTAX     PerfCounter64
     MAX-ACCESS read-only
     STATUS     current
     DESCRIPTION
         "Specifies current counter for total number of MAC Table entries that have 
          been or would have been learned, but have been failed due to a lack of 
          storage space in the Filtering Database."
     ::= { f3MPFlowStatsEntry 7 }

f3MPFlowStatsFDProtLearn OBJECT-TYPE
     SYNTAX     PerfCounter64
     MAX-ACCESS read-only
     STATUS     current
     DESCRIPTION
         "Specifies current counter for number 
          of frames dropped - protection learning."
     ::= { f3MPFlowStatsEntry 8 }

--
-- MP Flow History Statistics Table
--

f3MPFlowHistoryTable OBJECT-TYPE
    SYNTAX      SEQUENCE OF F3MPFlowHistoryEntry
    MAX-ACCESS  not-accessible
    STATUS      current
    DESCRIPTION
            "A collection of MP Flow statistics.  
             These reflect the history data."
    ::= { f3FpmPerfObjects 8 }

f3MPFlowHistoryEntry OBJECT-TYPE
    SYNTAX      F3MPFlowHistoryEntry 
    MAX-ACCESS  not-accessible
    STATUS      current
    DESCRIPTION
            "A conceptual row in the f3MPFlowHistoryTable.
             Entries exist in this table for each MP Flow."
    INDEX { neIndex, cmMPFlowIndex, f3MPFlowStatsIndex, f3MPFlowHistoryIndex }
    ::= { f3MPFlowHistoryTable 1 }

F3MPFlowHistoryEntry ::= SEQUENCE {
    f3MPFlowHistoryIndex                 Integer32,
    f3MPFlowHistoryTime                  DateAndTime,
    f3MPFlowHistoryValid                 TruthValue,
    f3MPFlowHistoryAction                CmPmBinAction,
    f3MPFlowHistoryFDStaticBlock         PerfCounter64,
    f3MPFlowHistoryFDHairPin             PerfCounter64,
    f3MPFlowHistoryMacTableDiscards      PerfCounter64, 
    f3MPFlowHistoryFDProtLearn           PerfCounter64
}

f3MPFlowHistoryIndex OBJECT-TYPE
    SYNTAX      Integer32 (1..65535)
    MAX-ACCESS  read-only
    STATUS      current
    DESCRIPTION
            "An arbitrary integer index value used to uniquely identify
             this MP Flow History statistics entry. Index 1 corresponds to 15minute, 
             index 2 to 1 day and index 3 corresponds to rollover."
    ::= { f3MPFlowHistoryEntry 1 }

f3MPFlowHistoryTime OBJECT-TYPE
    SYNTAX      DateAndTime
    MAX-ACCESS  read-only
    STATUS      current
    DESCRIPTION
            "Indicates the time of history bin creation."
    ::= { f3MPFlowHistoryEntry 2 }

f3MPFlowHistoryValid OBJECT-TYPE
    SYNTAX      TruthValue
    MAX-ACCESS  read-only
    STATUS      current
    DESCRIPTION
            "Indicates the validity of the bin."
    ::= { f3MPFlowHistoryEntry 3 }

f3MPFlowHistoryAction OBJECT-TYPE
    SYNTAX      CmPmBinAction
    MAX-ACCESS  read-write
    STATUS      current
    DESCRIPTION
            "Allows the Manager to clear the bin."
    ::= { f3MPFlowHistoryEntry 4 }

f3MPFlowHistoryFDStaticBlock OBJECT-TYPE
     SYNTAX     PerfCounter64
     MAX-ACCESS read-only
     STATUS     current
     DESCRIPTION
         "Specifies history bin for number of frames discarded due to a 
          static entry in Mac Table."
     ::= { f3MPFlowHistoryEntry 5 }

f3MPFlowHistoryFDHairPin OBJECT-TYPE
     SYNTAX     PerfCounter64
     MAX-ACCESS read-only
     STATUS     current
     DESCRIPTION
         "Specifies history bin for number of frames discarded because 
          destination Port is the ingress flowpoint or destination Port is in the 
          same Split Horizon Group."
     ::= { f3MPFlowHistoryEntry 6 }

f3MPFlowHistoryMacTableDiscards OBJECT-TYPE
     SYNTAX     PerfCounter64
     MAX-ACCESS read-only
     STATUS     current
     DESCRIPTION
         "Specifies history bin for total number of MAC Table entries that have 
          been or would have been learned, but have been failed due to a lack of 
          storage space in the Filtering Database."
     ::= { f3MPFlowHistoryEntry 7 }

f3MPFlowHistoryFDProtLearn OBJECT-TYPE
     SYNTAX     PerfCounter64
     MAX-ACCESS read-only
     STATUS     current
     DESCRIPTION
         "Specifies history bin for total number 
          of frames dropped - protection learning."
     ::= { f3MPFlowHistoryEntry 8 }

--
-- MP Flow Threshold Table
--

f3MPFlowThresholdTable OBJECT-TYPE
    SYNTAX      SEQUENCE OF F3MPFlowThresholdEntry
    MAX-ACCESS  not-accessible
    STATUS      current
    DESCRIPTION
            "A table of entries that allow manageability of MP Flow Thresholds."
    ::= { f3FpmPerfObjects 9 }

f3MPFlowThresholdEntry OBJECT-TYPE
    SYNTAX      F3MPFlowThresholdEntry
    MAX-ACCESS  not-accessible
    STATUS      current
    DESCRIPTION
            "A conceptual row in the f3MPFlowThresholdTable."
    INDEX { neIndex, cmMPFlowIndex, f3MPFlowStatsIndex, f3MPFlowThresholdIndex }
    ::= { f3MPFlowThresholdTable 1 }

F3MPFlowThresholdEntry ::= SEQUENCE {
    f3MPFlowThresholdIndex       Integer32,
    f3MPFlowThresholdInterval    CmPmIntervalType,
    f3MPFlowThresholdVariable    VariablePointer,
    f3MPFlowThresholdValueLo     Unsigned32,
    f3MPFlowThresholdValueHi     Unsigned32,
    f3MPFlowThresholdMonValue    Counter64
}

f3MPFlowThresholdIndex OBJECT-TYPE
    SYNTAX     Integer32 (1..65535)
    MAX-ACCESS read-only
    STATUS     current
    DESCRIPTION
        "An index that uniquely identifies an entry in the
         f3MPFlowThresholdTable."
    ::= { f3MPFlowThresholdEntry 1 }

f3MPFlowThresholdInterval OBJECT-TYPE
    SYNTAX     CmPmIntervalType
    MAX-ACCESS read-only
    STATUS     current
    DESCRIPTION
        "The interval over which monitored value is
         sampled and compared with the specified threshold."
    ::= { f3MPFlowThresholdEntry 2 }

f3MPFlowThresholdVariable OBJECT-TYPE
    SYNTAX     VariablePointer
    MAX-ACCESS read-only
    STATUS     current
    DESCRIPTION
        "The object identifier of the particular variable to be sampled."
    ::= { f3MPFlowThresholdEntry 3 }

f3MPFlowThresholdValueLo OBJECT-TYPE
    SYNTAX     Unsigned32
    MAX-ACCESS read-write
    STATUS     current
    DESCRIPTION
        "Lower 32 bits of the threshold value."
    ::= { f3MPFlowThresholdEntry 4 }

f3MPFlowThresholdValueHi OBJECT-TYPE
    SYNTAX     Unsigned32
    MAX-ACCESS read-write
    STATUS     current
    DESCRIPTION
        "Higher 32 bits of the threshold value."
    ::= { f3MPFlowThresholdEntry 5 }

f3MPFlowThresholdMonValue OBJECT-TYPE
    SYNTAX     Counter64
    MAX-ACCESS read-only
    STATUS     current
    DESCRIPTION
        "Monitored value corresponding to f3MPFlowThresholdVariable."
    ::= { f3MPFlowThresholdEntry 6 }

--
-- Access Flow Point QoS Shaper Current Statistics Table
--

f3AccFpQosShaperStatsTable OBJECT-TYPE
    SYNTAX      SEQUENCE OF F3AccFpQosShaperStatsEntry
    MAX-ACCESS  not-accessible
    STATUS      current
    DESCRIPTION
            "A collection of Acc FlowPoint QOS Shaper statistics.  
             These reflect the current data."
    ::= { f3FpmPerfObjects 10 }

f3AccFpQosShaperStatsEntry OBJECT-TYPE
    SYNTAX      F3AccFpQosShaperStatsEntry 
    MAX-ACCESS  not-accessible
    STATUS      current
    DESCRIPTION
            "A conceptual row in the f3AccFpQosShaperStatsTable.
             Entries exist in this table for each FlowPoint QoS Shaper."
    INDEX { neIndex, shelfIndex, slotIndex, cmEthernetAccPortIndex,
            f3AccFlowPointIndex, f3AccFpQosShaperIndex, 
            f3AccFpQosShaperStatsIndex }
    ::= { f3AccFpQosShaperStatsTable 1 }

F3AccFpQosShaperStatsEntry ::= SEQUENCE {
    f3AccFpQosShaperStatsIndex             Integer32,
    f3AccFpQosShaperStatsIntervalType      CmPmIntervalType,
    f3AccFpQosShaperStatsValid             TruthValue,
    f3AccFpQosShaperStatsAction            CmPmBinAction,
    f3AccFpQosShaperStatsBT                PerfCounter64,
    f3AccFpQosShaperStatsBTD               PerfCounter64,
    f3AccFpQosShaperStatsFD                PerfCounter64,
    f3AccFpQosShaperStatsFTD               PerfCounter64,
    f3AccFpQosShaperStatsABRRL             PerfCounter64,
    f3AccFpQosShaperStatsBREDD             PerfCounter64,
    f3AccFpQosShaperStatsFREDD             PerfCounter64
}

f3AccFpQosShaperStatsIndex OBJECT-TYPE
    SYNTAX      Integer32 (1..65535)
    MAX-ACCESS  read-only
    STATUS      current
    DESCRIPTION
            "An arbitrary integer index value used to uniquely identify
            this QOS Shaper statistics entry.
            1 - 15min
            2 - 1day
            3 - rollover
            4 - 5min"
    ::= { f3AccFpQosShaperStatsEntry 1 }

f3AccFpQosShaperStatsIntervalType OBJECT-TYPE
    SYNTAX      CmPmIntervalType
    MAX-ACCESS  read-only
    STATUS      current
    DESCRIPTION
            "Interval over which Performance Monitoring data is collected."
    ::= { f3AccFpQosShaperStatsEntry 2 }

f3AccFpQosShaperStatsValid OBJECT-TYPE
    SYNTAX      TruthValue
    MAX-ACCESS  read-only
    STATUS      current
    DESCRIPTION
            "Indicates the validity of the bin."
    ::= { f3AccFpQosShaperStatsEntry 3 }

f3AccFpQosShaperStatsAction OBJECT-TYPE
    SYNTAX      CmPmBinAction
    MAX-ACCESS  read-write
    STATUS      current
    DESCRIPTION
            "Allows the Manager to clear the bin."
    ::= { f3AccFpQosShaperStatsEntry 4 }

f3AccFpQosShaperStatsBT OBJECT-TYPE
     SYNTAX     PerfCounter64
     MAX-ACCESS read-only
     STATUS     current
     DESCRIPTION
         "Bytes Transmitted."
     ::= { f3AccFpQosShaperStatsEntry 5 }

f3AccFpQosShaperStatsBTD OBJECT-TYPE
     SYNTAX     PerfCounter64
     MAX-ACCESS read-only
     STATUS     current
     DESCRIPTION
         "Bytes Tail Dropped."
     ::= { f3AccFpQosShaperStatsEntry 6 }

f3AccFpQosShaperStatsFD OBJECT-TYPE
     SYNTAX     PerfCounter64
     MAX-ACCESS read-only
     STATUS     current
     DESCRIPTION
         "Frames Dequeued."
     ::= { f3AccFpQosShaperStatsEntry 7 }

f3AccFpQosShaperStatsFTD OBJECT-TYPE
     SYNTAX     PerfCounter64
     MAX-ACCESS read-only
     STATUS     current
     DESCRIPTION
         "Frames Tail Dropped."
     ::= { f3AccFpQosShaperStatsEntry 8 }

f3AccFpQosShaperStatsABRRL OBJECT-TYPE
     SYNTAX     PerfCounter64
     MAX-ACCESS read-only
     STATUS     current
     DESCRIPTION
         "Average Bit Rate - Rate Limited."
     ::= { f3AccFpQosShaperStatsEntry 9 }

f3AccFpQosShaperStatsBREDD OBJECT-TYPE
     SYNTAX     PerfCounter64
     MAX-ACCESS read-only
     STATUS     current
     DESCRIPTION
         "Bytes Random Early Discard, Dropped."
     ::= { f3AccFpQosShaperStatsEntry 10 }

f3AccFpQosShaperStatsFREDD OBJECT-TYPE
     SYNTAX     PerfCounter64
     MAX-ACCESS read-only
     STATUS     current
     DESCRIPTION
         "Frames Random Early Discard, Dropped."
     ::= { f3AccFpQosShaperStatsEntry 11 }

--
-- Access Flow Point QoS Shaper History Statistics Table
--

f3AccFpQosShaperHistoryTable OBJECT-TYPE
    SYNTAX      SEQUENCE OF F3AccFpQosShaperHistoryEntry
    MAX-ACCESS  not-accessible
    STATUS      current
    DESCRIPTION
            "A collection of Acc FlowPoint QOS Shaper statistics.  
             These reflect the history data."
    ::= { f3FpmPerfObjects 11 }

f3AccFpQosShaperHistoryEntry OBJECT-TYPE
    SYNTAX      F3AccFpQosShaperHistoryEntry 
    MAX-ACCESS  not-accessible
    STATUS      current
    DESCRIPTION
            "A conceptual row in the f3AccFpQosShaperHistoryTable.
             Entries exist in this table for each FlowPoint QoS Shaper."
    INDEX { neIndex, shelfIndex, slotIndex, cmEthernetAccPortIndex,
            f3AccFlowPointIndex, f3AccFpQosShaperIndex, 
            f3AccFpQosShaperStatsIndex, f3AccFpQosShaperHistoryIndex }
    ::= { f3AccFpQosShaperHistoryTable 1 }

F3AccFpQosShaperHistoryEntry ::= SEQUENCE {
    f3AccFpQosShaperHistoryIndex             Integer32,
    f3AccFpQosShaperHistoryTime              DateAndTime,
    f3AccFpQosShaperHistoryValid             TruthValue,
    f3AccFpQosShaperHistoryAction            CmPmBinAction,
    f3AccFpQosShaperHistoryBT                PerfCounter64,
    f3AccFpQosShaperHistoryBTD               PerfCounter64,
    f3AccFpQosShaperHistoryFD                PerfCounter64,
    f3AccFpQosShaperHistoryFTD               PerfCounter64,
    f3AccFpQosShaperHistoryABRRL             PerfCounter64,
    f3AccFpQosShaperHistoryBREDD             PerfCounter64,
    f3AccFpQosShaperHistoryFREDD             PerfCounter64
}

f3AccFpQosShaperHistoryIndex OBJECT-TYPE
    SYNTAX      Integer32 (1..65535)
    MAX-ACCESS  read-only
    STATUS      current
    DESCRIPTION
            "An arbitrary integer index value used to uniquely identify
            this QOS Shaper statistics entry."
    ::= { f3AccFpQosShaperHistoryEntry 1 }

f3AccFpQosShaperHistoryTime OBJECT-TYPE
    SYNTAX      DateAndTime
    MAX-ACCESS  read-only
    STATUS      current
    DESCRIPTION
            "Indicates the time of history bin creation." 
    ::= { f3AccFpQosShaperHistoryEntry 2 }

f3AccFpQosShaperHistoryValid OBJECT-TYPE
    SYNTAX      TruthValue
    MAX-ACCESS  read-only
    STATUS      current
    DESCRIPTION
            "Indicates the validity of the bin."
    ::= { f3AccFpQosShaperHistoryEntry 3 }

f3AccFpQosShaperHistoryAction OBJECT-TYPE
    SYNTAX      CmPmBinAction
    MAX-ACCESS  read-write
    STATUS      current
    DESCRIPTION
            "Allows the Manager to clear the bin."
    ::= { f3AccFpQosShaperHistoryEntry 4 }

f3AccFpQosShaperHistoryBT OBJECT-TYPE
     SYNTAX     PerfCounter64
     MAX-ACCESS read-only
     STATUS     current
     DESCRIPTION
         "Bytes Transmitted."
     ::= { f3AccFpQosShaperHistoryEntry 5 }

f3AccFpQosShaperHistoryBTD OBJECT-TYPE
     SYNTAX     PerfCounter64
     MAX-ACCESS read-only
     STATUS     current
     DESCRIPTION
         "Bytes Tail Dropped."
     ::= { f3AccFpQosShaperHistoryEntry 6 }

f3AccFpQosShaperHistoryFD OBJECT-TYPE
     SYNTAX     PerfCounter64
     MAX-ACCESS read-only
     STATUS     current
     DESCRIPTION
         "Frames Dequeued."
     ::= { f3AccFpQosShaperHistoryEntry 7 }

f3AccFpQosShaperHistoryFTD OBJECT-TYPE
     SYNTAX     PerfCounter64
     MAX-ACCESS read-only
     STATUS     current
     DESCRIPTION
         "Frames Tail Dropped."
     ::= { f3AccFpQosShaperHistoryEntry 8 }

f3AccFpQosShaperHistoryABRRL OBJECT-TYPE
     SYNTAX     PerfCounter64
     MAX-ACCESS read-only
     STATUS     current
     DESCRIPTION
         "Average Bit Rate - Rate Limited."
     ::= { f3AccFpQosShaperHistoryEntry 9 }

f3AccFpQosShaperHistoryBREDD OBJECT-TYPE
     SYNTAX     PerfCounter64
     MAX-ACCESS read-only
     STATUS     current
     DESCRIPTION
         "Bytes Random Early Discard, Dropped."
     ::= { f3AccFpQosShaperHistoryEntry 10 }

f3AccFpQosShaperHistoryFREDD OBJECT-TYPE
     SYNTAX     PerfCounter64
     MAX-ACCESS read-only
     STATUS     current
     DESCRIPTION
         "Frames Random Early Discard, Dropped."
     ::= { f3AccFpQosShaperHistoryEntry 11 }

--
-- Access Flow Point QoS Shaper Threshold Table
--

f3AccFpQosShaperThresholdTable OBJECT-TYPE
    SYNTAX      SEQUENCE OF F3AccFpQosShaperThresholdEntry
    MAX-ACCESS  not-accessible
    STATUS      current
    DESCRIPTION
            "A table of entries that allow manageability of Acc FlowPoint
             QoS Shaper Thresholds."
    ::= { f3FpmPerfObjects 12 }

f3AccFpQosShaperThresholdEntry OBJECT-TYPE
    SYNTAX      F3AccFpQosShaperThresholdEntry
    MAX-ACCESS  not-accessible
    STATUS      current
    DESCRIPTION
            "A conceptual row in the f3AccFpQosShaperThresholdTable."
    INDEX { neIndex, shelfIndex, slotIndex, cmEthernetAccPortIndex,
            f3AccFlowPointIndex, f3AccFpQosShaperIndex, 
            f3AccFpQosShaperStatsIndex, f3AccFpQosShaperThresholdIndex }
    ::= { f3AccFpQosShaperThresholdTable 1 }

F3AccFpQosShaperThresholdEntry ::= SEQUENCE {
    f3AccFpQosShaperThresholdIndex       Integer32,
    f3AccFpQosShaperThresholdInterval    CmPmIntervalType,
    f3AccFpQosShaperThresholdVariable    VariablePointer,
    f3AccFpQosShaperThresholdValueLo     Unsigned32,
    f3AccFpQosShaperThresholdValueHi     Unsigned32,
    f3AccFpQosShaperThresholdMonValue    Counter64
}

f3AccFpQosShaperThresholdIndex OBJECT-TYPE
    SYNTAX     Integer32 (1..65535)
    MAX-ACCESS read-only
    STATUS     current
    DESCRIPTION
        "An index that uniquely identifies an entry in the
        f3AccFpQosShaperThresholdTable."
    ::= { f3AccFpQosShaperThresholdEntry 1 }

f3AccFpQosShaperThresholdInterval OBJECT-TYPE
    SYNTAX     CmPmIntervalType
    MAX-ACCESS read-only
    STATUS     current
    DESCRIPTION
        "The interval over which monitored value is
        sampled and compared with the specified threshold."
    ::= { f3AccFpQosShaperThresholdEntry 2 }

f3AccFpQosShaperThresholdVariable OBJECT-TYPE
    SYNTAX     VariablePointer
    MAX-ACCESS read-only
    STATUS     current
    DESCRIPTION
        "The object identifier of the particular variable to be
        sampled."
    ::= { f3AccFpQosShaperThresholdEntry 3 }

f3AccFpQosShaperThresholdValueLo OBJECT-TYPE
    SYNTAX     Unsigned32
    MAX-ACCESS read-write
    STATUS     current
    DESCRIPTION
        "Lower 32 bits of the threshold value."
    ::= { f3AccFpQosShaperThresholdEntry 4 }

f3AccFpQosShaperThresholdValueHi OBJECT-TYPE
    SYNTAX     Unsigned32
    MAX-ACCESS read-write
    STATUS     current
    DESCRIPTION
        "Higher 32 bits of the threshold value."
    ::= { f3AccFpQosShaperThresholdEntry 5 }

f3AccFpQosShaperThresholdMonValue OBJECT-TYPE
    SYNTAX     Counter64
    MAX-ACCESS read-only
    STATUS     current
    DESCRIPTION
        "Monitored value corresponding to f3AccFpQosShaperThresholdVariable."
    ::= { f3AccFpQosShaperThresholdEntry 6 }

--
-- Network Flow Point QoS Shaper Current Statistics Table
--

f3NetFpQosShaperStatsTable OBJECT-TYPE
    SYNTAX      SEQUENCE OF F3NetFpQosShaperStatsEntry
    MAX-ACCESS  not-accessible
    STATUS      current
    DESCRIPTION
            "A collection of Net FlowPoint QOS Shaper statistics.  
             These reflect the current data."
    ::= { f3FpmPerfObjects 13 }

f3NetFpQosShaperStatsEntry OBJECT-TYPE
    SYNTAX      F3NetFpQosShaperStatsEntry 
    MAX-ACCESS  not-accessible
    STATUS      current
    DESCRIPTION
            "A conceptual row in the f3NetFpQosShaperStatsTable.
             Entries exist in this table for each FlowPoint QoS Shaper."
    INDEX { neIndex, shelfIndex, slotIndex, cmEthernetNetPortIndex,
            f3NetFlowPointIndex, f3NetFpQosShaperIndex, 
            f3NetFpQosShaperStatsIndex }
    ::= { f3NetFpQosShaperStatsTable 1 }

F3NetFpQosShaperStatsEntry ::= SEQUENCE {
    f3NetFpQosShaperStatsIndex             Integer32,
    f3NetFpQosShaperStatsIntervalType      CmPmIntervalType,
    f3NetFpQosShaperStatsValid             TruthValue,
    f3NetFpQosShaperStatsAction            CmPmBinAction,
    f3NetFpQosShaperStatsBT                PerfCounter64,
    f3NetFpQosShaperStatsBTD               PerfCounter64,
    f3NetFpQosShaperStatsFD                PerfCounter64,
    f3NetFpQosShaperStatsFTD               PerfCounter64,
    f3NetFpQosShaperStatsABRRL             PerfCounter64,
    f3NetFpQosShaperStatsBREDD             PerfCounter64,
    f3NetFpQosShaperStatsFREDD             PerfCounter64
}

f3NetFpQosShaperStatsIndex OBJECT-TYPE
    SYNTAX      Integer32 (1..65535)
    MAX-ACCESS  read-only
    STATUS      current
    DESCRIPTION
            "An arbitrary integer index value used to uniquely identify
            this QOS Shaper statistics entry.
            1 - 15min
            2 - 1day
            3 - rollover
            4 - 5min"
    ::= { f3NetFpQosShaperStatsEntry 1 }

f3NetFpQosShaperStatsIntervalType OBJECT-TYPE
    SYNTAX      CmPmIntervalType
    MAX-ACCESS  read-only
    STATUS      current
    DESCRIPTION
            "Interval over which Performance Monitoring data is collected."
    ::= { f3NetFpQosShaperStatsEntry 2 }

f3NetFpQosShaperStatsValid OBJECT-TYPE
    SYNTAX      TruthValue
    MAX-ACCESS  read-only
    STATUS      current
    DESCRIPTION
            "Indicates the validity of the bin."
    ::= { f3NetFpQosShaperStatsEntry 3 }

f3NetFpQosShaperStatsAction OBJECT-TYPE
    SYNTAX      CmPmBinAction
    MAX-ACCESS  read-write
    STATUS      current
    DESCRIPTION
            "Allows the Manager to clear the bin."
    ::= { f3NetFpQosShaperStatsEntry 4 }

f3NetFpQosShaperStatsBT OBJECT-TYPE
     SYNTAX     PerfCounter64
     MAX-ACCESS read-only
     STATUS     current
     DESCRIPTION
         "Bytes Transmitted."
     ::= { f3NetFpQosShaperStatsEntry 5 }

f3NetFpQosShaperStatsBTD OBJECT-TYPE
     SYNTAX     PerfCounter64
     MAX-ACCESS read-only
     STATUS     current
     DESCRIPTION
         "Bytes Tail Dropped."
     ::= { f3NetFpQosShaperStatsEntry 6 }

f3NetFpQosShaperStatsFD OBJECT-TYPE
     SYNTAX     PerfCounter64
     MAX-ACCESS read-only
     STATUS     current
     DESCRIPTION
         "Frames Dequeued."
     ::= { f3NetFpQosShaperStatsEntry 7 }

f3NetFpQosShaperStatsFTD OBJECT-TYPE
     SYNTAX     PerfCounter64
     MAX-ACCESS read-only
     STATUS     current
     DESCRIPTION
         "Frames Tail Dropped."
     ::= { f3NetFpQosShaperStatsEntry 8 }

f3NetFpQosShaperStatsABRRL OBJECT-TYPE
     SYNTAX     PerfCounter64
     MAX-ACCESS read-only
     STATUS     current
     DESCRIPTION
         "Average Bit Rate - Rate Limited."
     ::= { f3NetFpQosShaperStatsEntry 9 }

f3NetFpQosShaperStatsBREDD OBJECT-TYPE
     SYNTAX     PerfCounter64
     MAX-ACCESS read-only
     STATUS     current
     DESCRIPTION
         "Bytes Random Early Discard, Dropped."
     ::= { f3NetFpQosShaperStatsEntry 10 }

f3NetFpQosShaperStatsFREDD OBJECT-TYPE
     SYNTAX     PerfCounter64
     MAX-ACCESS read-only
     STATUS     current
     DESCRIPTION
         "Frames Random Early Discard, Dropped."
     ::= { f3NetFpQosShaperStatsEntry 11 }

--
-- Network Flow Point QoS Shaper History Statistics Table
--

f3NetFpQosShaperHistoryTable OBJECT-TYPE
    SYNTAX      SEQUENCE OF F3NetFpQosShaperHistoryEntry
    MAX-ACCESS  not-accessible
    STATUS      current
    DESCRIPTION
            "A collection of Net FlowPoint QOS Shaper statistics.  
             These reflect the history data."
    ::= { f3FpmPerfObjects 14 }

f3NetFpQosShaperHistoryEntry OBJECT-TYPE
    SYNTAX      F3NetFpQosShaperHistoryEntry 
    MAX-ACCESS  not-accessible
    STATUS      current
    DESCRIPTION
            "A conceptual row in the f3NetFpQosShaperHistoryTable.
             Entries exist in this table for each FlowPoint QoS Shaper."
    INDEX { neIndex, shelfIndex, slotIndex, cmEthernetNetPortIndex,
            f3NetFlowPointIndex, f3NetFpQosShaperIndex, 
            f3NetFpQosShaperStatsIndex, f3NetFpQosShaperHistoryIndex }
    ::= { f3NetFpQosShaperHistoryTable 1 }

F3NetFpQosShaperHistoryEntry ::= SEQUENCE {
    f3NetFpQosShaperHistoryIndex             Integer32,
    f3NetFpQosShaperHistoryTime              DateAndTime,
    f3NetFpQosShaperHistoryValid             TruthValue,
    f3NetFpQosShaperHistoryAction            CmPmBinAction,
    f3NetFpQosShaperHistoryBT                PerfCounter64,
    f3NetFpQosShaperHistoryBTD               PerfCounter64,
    f3NetFpQosShaperHistoryFD                PerfCounter64,
    f3NetFpQosShaperHistoryFTD               PerfCounter64,
    f3NetFpQosShaperHistoryABRRL             PerfCounter64,
    f3NetFpQosShaperHistoryBREDD             PerfCounter64,
    f3NetFpQosShaperHistoryFREDD             PerfCounter64
}

f3NetFpQosShaperHistoryIndex OBJECT-TYPE
    SYNTAX      Integer32 (1..65535)
    MAX-ACCESS  read-only
    STATUS      current
    DESCRIPTION
            "An arbitrary integer index value used to uniquely identify
            this QOS Shaper statistics entry."
    ::= { f3NetFpQosShaperHistoryEntry 1 }

f3NetFpQosShaperHistoryTime OBJECT-TYPE
    SYNTAX      DateAndTime
    MAX-ACCESS  read-only
    STATUS      current
    DESCRIPTION
            "Indicates the time of history bin creation." 
    ::= { f3NetFpQosShaperHistoryEntry 2 }

f3NetFpQosShaperHistoryValid OBJECT-TYPE
    SYNTAX      TruthValue
    MAX-ACCESS  read-only
    STATUS      current
    DESCRIPTION
            "Indicates the validity of the bin."
    ::= { f3NetFpQosShaperHistoryEntry 3 }

f3NetFpQosShaperHistoryAction OBJECT-TYPE
    SYNTAX      CmPmBinAction
    MAX-ACCESS  read-write
    STATUS      current
    DESCRIPTION
            "Allows the Manager to clear the bin."
    ::= { f3NetFpQosShaperHistoryEntry 4 }

f3NetFpQosShaperHistoryBT OBJECT-TYPE
     SYNTAX     PerfCounter64
     MAX-ACCESS read-only
     STATUS     current
     DESCRIPTION
         "Bytes Transmitted."
     ::= { f3NetFpQosShaperHistoryEntry 5 }

f3NetFpQosShaperHistoryBTD OBJECT-TYPE
     SYNTAX     PerfCounter64
     MAX-ACCESS read-only
     STATUS     current
     DESCRIPTION
         "Bytes Tail Dropped."
     ::= { f3NetFpQosShaperHistoryEntry 6 }

f3NetFpQosShaperHistoryFD OBJECT-TYPE
     SYNTAX     PerfCounter64
     MAX-ACCESS read-only
     STATUS     current
     DESCRIPTION
         "Frames Dequeued."
     ::= { f3NetFpQosShaperHistoryEntry 7 }

f3NetFpQosShaperHistoryFTD OBJECT-TYPE
     SYNTAX     PerfCounter64
     MAX-ACCESS read-only
     STATUS     current
     DESCRIPTION
         "Frames Tail Dropped."
     ::= { f3NetFpQosShaperHistoryEntry 8 }

f3NetFpQosShaperHistoryABRRL OBJECT-TYPE
     SYNTAX     PerfCounter64
     MAX-ACCESS read-only
     STATUS     current
     DESCRIPTION
         "Average Bit Rate - Rate Limited."
     ::= { f3NetFpQosShaperHistoryEntry 9 }

f3NetFpQosShaperHistoryBREDD OBJECT-TYPE
     SYNTAX     PerfCounter64
     MAX-ACCESS read-only
     STATUS     current
     DESCRIPTION
         "Bytes Random Early Discard, Dropped."
     ::= { f3NetFpQosShaperHistoryEntry 10 }

f3NetFpQosShaperHistoryFREDD OBJECT-TYPE
     SYNTAX     PerfCounter64
     MAX-ACCESS read-only
     STATUS     current
     DESCRIPTION
         "Frames Random Early Discard, Dropped."
     ::= { f3NetFpQosShaperHistoryEntry 11 }

--
-- Network Flow Point QoS Shaper Threshold Table
--

f3NetFpQosShaperThresholdTable OBJECT-TYPE
    SYNTAX      SEQUENCE OF F3NetFpQosShaperThresholdEntry
    MAX-ACCESS  not-accessible
    STATUS      current
    DESCRIPTION
            "A table of entries that allow manageability of Net FlowPoint
             QoS Shaper Thresholds."
    ::= { f3FpmPerfObjects 15 }

f3NetFpQosShaperThresholdEntry OBJECT-TYPE
    SYNTAX      F3NetFpQosShaperThresholdEntry
    MAX-ACCESS  not-accessible
    STATUS      current
    DESCRIPTION
            "A conceptual row in the f3NetFpQosShaperThresholdTable."
    INDEX { neIndex, shelfIndex, slotIndex, cmEthernetNetPortIndex,
            f3NetFlowPointIndex, f3NetFpQosShaperIndex, 
            f3NetFpQosShaperStatsIndex, f3NetFpQosShaperThresholdIndex }
    ::= { f3NetFpQosShaperThresholdTable 1 }

F3NetFpQosShaperThresholdEntry ::= SEQUENCE {
    f3NetFpQosShaperThresholdIndex       Integer32,
    f3NetFpQosShaperThresholdInterval    CmPmIntervalType,
    f3NetFpQosShaperThresholdVariable    VariablePointer,
    f3NetFpQosShaperThresholdValueLo     Unsigned32,
    f3NetFpQosShaperThresholdValueHi     Unsigned32,
    f3NetFpQosShaperThresholdMonValue    Counter64
}

f3NetFpQosShaperThresholdIndex OBJECT-TYPE
    SYNTAX     Integer32 (1..65535)
    MAX-ACCESS read-only
    STATUS     current
    DESCRIPTION
        "An index that uniquely identifies an entry in the
        f3NetFpQosShaperThresholdTable."
    ::= { f3NetFpQosShaperThresholdEntry 1 }

f3NetFpQosShaperThresholdInterval OBJECT-TYPE
    SYNTAX     CmPmIntervalType
    MAX-ACCESS read-only
    STATUS     current
    DESCRIPTION
        "The interval over which monitored value is
        sampled and compared with the specified threshold."
    ::= { f3NetFpQosShaperThresholdEntry 2 }

f3NetFpQosShaperThresholdVariable OBJECT-TYPE
    SYNTAX     VariablePointer
    MAX-ACCESS read-only
    STATUS     current
    DESCRIPTION
        "The object identifier of the particular variable to be
        sampled."
    ::= { f3NetFpQosShaperThresholdEntry 3 }

f3NetFpQosShaperThresholdValueLo OBJECT-TYPE
    SYNTAX     Unsigned32
    MAX-ACCESS read-write
    STATUS     current
    DESCRIPTION
        "Lower 32 bits of the threshold value."
    ::= { f3NetFpQosShaperThresholdEntry 4 }

f3NetFpQosShaperThresholdValueHi OBJECT-TYPE
    SYNTAX     Unsigned32
    MAX-ACCESS read-write
    STATUS     current
    DESCRIPTION
        "Higher 32 bits of the threshold value."
    ::= { f3NetFpQosShaperThresholdEntry 5 }

f3NetFpQosShaperThresholdMonValue OBJECT-TYPE
    SYNTAX     Counter64
    MAX-ACCESS read-only
    STATUS     current
    DESCRIPTION
        "Monitored value corresponding to f3NetFpQosShaperThresholdVariable."
    ::= { f3NetFpQosShaperThresholdEntry 6 }

--
-- Access Flow Point QoS Policer Current Statistics Table
--

f3AccFpQosPolicerStatsTable OBJECT-TYPE
    SYNTAX      SEQUENCE OF F3AccFpQosPolicerStatsEntry
    MAX-ACCESS  not-accessible
    STATUS      current
    DESCRIPTION
            "A collection of Acc FlowPoint QOS Policer statistics.  
             These reflect the current data."
    ::= { f3FpmPerfObjects 16 }

f3AccFpQosPolicerStatsEntry OBJECT-TYPE
    SYNTAX      F3AccFpQosPolicerStatsEntry 
    MAX-ACCESS  not-accessible
    STATUS      current
    DESCRIPTION
            "A conceptual row in the f3AccFpQosPolicerStatsTable.
             Entries exist in this table for each Acc FlowPoint QoS Policer."
    INDEX { neIndex, shelfIndex, slotIndex, cmEthernetAccPortIndex, 
            f3AccFlowPointIndex, f3AccFpQosPolicerIndex, f3AccFpQosPolicerStatsIndex }
    ::= { f3AccFpQosPolicerStatsTable 1 }

F3AccFpQosPolicerStatsEntry ::= SEQUENCE {
    f3AccFpQosPolicerStatsIndex           Integer32,
    f3AccFpQosPolicerStatsIntervalType    CmPmIntervalType,
    f3AccFpQosPolicerStatsValid           TruthValue,
    f3AccFpQosPolicerStatsAction          CmPmBinAction,
    f3AccFpQosPolicerStatsFMG             PerfCounter64,
    f3AccFpQosPolicerStatsFMY             PerfCounter64,
    f3AccFpQosPolicerStatsFMRD            PerfCounter64,
    f3AccFpQosPolicerStatsBytesIn         PerfCounter64,
    f3AccFpQosPolicerStatsBytesOut        PerfCounter64,
    f3AccFpQosPolicerStatsABR             PerfCounter64
}

f3AccFpQosPolicerStatsIndex OBJECT-TYPE
    SYNTAX      Integer32 (1..65535)
    MAX-ACCESS  read-only
    STATUS      current
    DESCRIPTION
            "An integer index value used to uniquely identify
            this QOS Policer statistics entry.
            1 - 15min
            2 - 1day
            3 - rollover
            4 - 5min"
    ::= { f3AccFpQosPolicerStatsEntry 1 }

f3AccFpQosPolicerStatsIntervalType OBJECT-TYPE
    SYNTAX      CmPmIntervalType
    MAX-ACCESS  read-only
    STATUS      current
    DESCRIPTION
            "Interval over which Performance Monitoring data is collected."
    ::= { f3AccFpQosPolicerStatsEntry 2 }

f3AccFpQosPolicerStatsValid OBJECT-TYPE
    SYNTAX      TruthValue
    MAX-ACCESS  read-only
    STATUS      current
    DESCRIPTION
            "Indicates the validity of the bin."
    ::= { f3AccFpQosPolicerStatsEntry 3 }

f3AccFpQosPolicerStatsAction OBJECT-TYPE
    SYNTAX      CmPmBinAction
    MAX-ACCESS  read-write
    STATUS      current
    DESCRIPTION
            "Allows the Manager to clear the bin."
    ::= { f3AccFpQosPolicerStatsEntry 4 }

f3AccFpQosPolicerStatsFMG OBJECT-TYPE
     SYNTAX     PerfCounter64
     MAX-ACCESS read-only
     STATUS     current
     DESCRIPTION
         "Frames Marked Green."
     ::= { f3AccFpQosPolicerStatsEntry 5 }

f3AccFpQosPolicerStatsFMY OBJECT-TYPE
     SYNTAX     PerfCounter64
     MAX-ACCESS read-only
     STATUS     current
     DESCRIPTION
         "Frames Marked Yellow."
     ::= { f3AccFpQosPolicerStatsEntry 6 }

f3AccFpQosPolicerStatsFMRD OBJECT-TYPE
     SYNTAX     PerfCounter64
     MAX-ACCESS read-only
     STATUS     current
     DESCRIPTION
         "Frames Marked Red and Discarded."
     ::= { f3AccFpQosPolicerStatsEntry 7 }

f3AccFpQosPolicerStatsBytesIn OBJECT-TYPE
     SYNTAX     PerfCounter64
     MAX-ACCESS read-only
     STATUS     current
     DESCRIPTION
         "Number of bytes received by the Policer."
     ::= { f3AccFpQosPolicerStatsEntry 8 }

f3AccFpQosPolicerStatsBytesOut OBJECT-TYPE
     SYNTAX     PerfCounter64
     MAX-ACCESS read-only
     STATUS     current
     DESCRIPTION
         "Number of bytes transmitted by the Policer."
     ::= { f3AccFpQosPolicerStatsEntry 9 }

f3AccFpQosPolicerStatsABR OBJECT-TYPE
     SYNTAX     PerfCounter64
     MAX-ACCESS read-only
     STATUS     current
     DESCRIPTION
         "Average Bit Rate  on the Policer."
     ::= { f3AccFpQosPolicerStatsEntry 10 }

--
-- Access Flow Point QoS Policer History Statistics Table
--

f3AccFpQosPolicerHistoryTable OBJECT-TYPE
    SYNTAX      SEQUENCE OF F3AccFpQosPolicerHistoryEntry
    MAX-ACCESS  not-accessible
    STATUS      current
    DESCRIPTION
            "A collection of Acc FlowPoint QOS Policer statistics.  
             These reflect the history data."
    ::= { f3FpmPerfObjects 17 }

f3AccFpQosPolicerHistoryEntry OBJECT-TYPE
    SYNTAX      F3AccFpQosPolicerHistoryEntry 
    MAX-ACCESS  not-accessible
    STATUS      current
    DESCRIPTION
            "A conceptual row in the f3AccFpQosPolicerHistoryTable.
             Entries exist in this table for each Acc FlowPoint QoS Policer."
    INDEX { neIndex, shelfIndex, slotIndex, cmEthernetAccPortIndex, 
            f3AccFlowPointIndex, f3AccFpQosPolicerIndex, 
            f3AccFpQosPolicerStatsIndex, f3AccFpQosPolicerHistoryIndex }
    ::= { f3AccFpQosPolicerHistoryTable 1 }

F3AccFpQosPolicerHistoryEntry ::= SEQUENCE {
    f3AccFpQosPolicerHistoryIndex           Integer32,
    f3AccFpQosPolicerHistoryTime            DateAndTime,
    f3AccFpQosPolicerHistoryValid           TruthValue,
    f3AccFpQosPolicerHistoryAction          CmPmBinAction,
    f3AccFpQosPolicerHistoryFMG             PerfCounter64,
    f3AccFpQosPolicerHistoryFMY             PerfCounter64,
    f3AccFpQosPolicerHistoryFMRD            PerfCounter64,
    f3AccFpQosPolicerHistoryBytesIn         PerfCounter64,
    f3AccFpQosPolicerHistoryBytesOut        PerfCounter64,
    f3AccFpQosPolicerHistoryABR             PerfCounter64
}

f3AccFpQosPolicerHistoryIndex OBJECT-TYPE
    SYNTAX      Integer32 (1..65535)
    MAX-ACCESS  read-only
    STATUS      current
    DESCRIPTION
            "An arbitrary integer index value used to uniquely identify
            this QOS Policer history entry."
    ::= { f3AccFpQosPolicerHistoryEntry 1 }

f3AccFpQosPolicerHistoryTime OBJECT-TYPE
    SYNTAX      DateAndTime
    MAX-ACCESS  read-only
    STATUS      current
    DESCRIPTION
            "Indicates the time of history bin creation." 
    ::= { f3AccFpQosPolicerHistoryEntry 2 }

f3AccFpQosPolicerHistoryValid OBJECT-TYPE
    SYNTAX      TruthValue
    MAX-ACCESS  read-only
    STATUS      current
    DESCRIPTION
            "Indicates the validity of the bin."
    ::= { f3AccFpQosPolicerHistoryEntry 3 }

f3AccFpQosPolicerHistoryAction OBJECT-TYPE
    SYNTAX      CmPmBinAction
    MAX-ACCESS  read-write
    STATUS      current
    DESCRIPTION
            "Allows the Manager to clear the bin."
    ::= { f3AccFpQosPolicerHistoryEntry 4 }

f3AccFpQosPolicerHistoryFMG OBJECT-TYPE
     SYNTAX     PerfCounter64
     MAX-ACCESS read-only
     STATUS     current
     DESCRIPTION
         "Frames Marked Green."
     ::= { f3AccFpQosPolicerHistoryEntry 5 }

f3AccFpQosPolicerHistoryFMY OBJECT-TYPE
     SYNTAX     PerfCounter64
     MAX-ACCESS read-only
     STATUS     current
     DESCRIPTION
         "Frames Marked Yellow."
     ::= { f3AccFpQosPolicerHistoryEntry 6 }

f3AccFpQosPolicerHistoryFMRD OBJECT-TYPE
     SYNTAX     PerfCounter64
     MAX-ACCESS read-only
     STATUS     current
     DESCRIPTION
         "Frames Marked Red and Discarded."
     ::= { f3AccFpQosPolicerHistoryEntry 7 }

f3AccFpQosPolicerHistoryBytesIn OBJECT-TYPE
     SYNTAX     PerfCounter64
     MAX-ACCESS read-only
     STATUS     current
     DESCRIPTION
         "Number of bytes received by the Policer."
     ::= { f3AccFpQosPolicerHistoryEntry 8 }

f3AccFpQosPolicerHistoryBytesOut OBJECT-TYPE
     SYNTAX     PerfCounter64
     MAX-ACCESS read-only
     STATUS     current
     DESCRIPTION
         "Number of bytes transmitted by the Policer."
     ::= { f3AccFpQosPolicerHistoryEntry 9 }

f3AccFpQosPolicerHistoryABR OBJECT-TYPE
     SYNTAX     PerfCounter64
     MAX-ACCESS read-only
     STATUS     current
     DESCRIPTION
         "Average Bit Rate  on the Policer."
     ::= { f3AccFpQosPolicerHistoryEntry 10 }

--
-- Access Flow Point QoS Policer Threshold Table
--

f3AccFpQosPolicerThresholdTable OBJECT-TYPE
    SYNTAX      SEQUENCE OF F3AccFpQosPolicerThresholdEntry
    MAX-ACCESS  not-accessible
    STATUS      current
    DESCRIPTION
            "A table of entries that allow manageability of QOS
             Policer Thresholds."
    ::= { f3FpmPerfObjects 18 }

f3AccFpQosPolicerThresholdEntry OBJECT-TYPE
    SYNTAX      F3AccFpQosPolicerThresholdEntry
    MAX-ACCESS  not-accessible
    STATUS      current
    DESCRIPTION
            "A conceptual row in the f3AccFpQosPolicerThresholdTable."
    INDEX { neIndex, shelfIndex, slotIndex, cmEthernetAccPortIndex, 
            f3AccFlowPointIndex, f3AccFpQosPolicerIndex, 
            f3AccFpQosPolicerStatsIndex, f3AccFpQosPolicerThresholdIndex }
    ::= { f3AccFpQosPolicerThresholdTable 1 }

F3AccFpQosPolicerThresholdEntry ::= SEQUENCE {
    f3AccFpQosPolicerThresholdIndex       Integer32,
    f3AccFpQosPolicerThresholdInterval    CmPmIntervalType,
    f3AccFpQosPolicerThresholdVariable    VariablePointer,
    f3AccFpQosPolicerThresholdValueLo     Unsigned32,
    f3AccFpQosPolicerThresholdValueHi     Unsigned32,
    f3AccFpQosPolicerThresholdMonValue    Counter64
}

f3AccFpQosPolicerThresholdIndex OBJECT-TYPE
    SYNTAX     Integer32 (1..65535)
    MAX-ACCESS read-only
    STATUS     current
    DESCRIPTION
        "An index that uniquely identifies an entry in the
        f3AccFpQosPolicerThresholdTable."
    ::= { f3AccFpQosPolicerThresholdEntry 1 }

f3AccFpQosPolicerThresholdInterval OBJECT-TYPE
    SYNTAX     CmPmIntervalType
    MAX-ACCESS read-only
    STATUS     current
    DESCRIPTION
        "The interval over which monitored value is
        sampled and compared with the specified threshold."
    ::= { f3AccFpQosPolicerThresholdEntry 2 }

f3AccFpQosPolicerThresholdVariable OBJECT-TYPE
    SYNTAX     VariablePointer
    MAX-ACCESS read-only
    STATUS     current
    DESCRIPTION
        "The object identifier of the particular variable to be
        sampled."
    ::= { f3AccFpQosPolicerThresholdEntry 3 }

f3AccFpQosPolicerThresholdValueLo OBJECT-TYPE
    SYNTAX     Unsigned32
    MAX-ACCESS read-write
    STATUS     current
    DESCRIPTION
        "Lower 32 bits of the threshold value."
    ::= { f3AccFpQosPolicerThresholdEntry 4 }

f3AccFpQosPolicerThresholdValueHi OBJECT-TYPE
    SYNTAX     Unsigned32
    MAX-ACCESS read-write
    STATUS     current
    DESCRIPTION
        "Higher 32 bits of the threshold value."
    ::= { f3AccFpQosPolicerThresholdEntry 5 }

f3AccFpQosPolicerThresholdMonValue OBJECT-TYPE
    SYNTAX     Counter64
    MAX-ACCESS read-only
    STATUS     current
    DESCRIPTION
        "Monitored value corresponding to f3AccFpQosPolicerThresholdVariable."
    ::= { f3AccFpQosPolicerThresholdEntry 6 }

--
-- Network Flow Point QoS Policer Current Statistics Table
--

f3NetFpQosPolicerStatsTable OBJECT-TYPE
    SYNTAX      SEQUENCE OF F3NetFpQosPolicerStatsEntry
    MAX-ACCESS  not-accessible
    STATUS      current
    DESCRIPTION
            "A collection of Net FlowPoint QOS Policer statistics.  
             These reflect the current data."
    ::= { f3FpmPerfObjects 19 }

f3NetFpQosPolicerStatsEntry OBJECT-TYPE
    SYNTAX      F3NetFpQosPolicerStatsEntry 
    MAX-ACCESS  not-accessible
    STATUS      current
    DESCRIPTION
            "A conceptual row in the f3NetFpQosPolicerStatsTable.
             Entries exist in this table for each Net FlowPoint QoS Policer."
    INDEX { neIndex, shelfIndex, slotIndex, cmEthernetNetPortIndex, 
            f3NetFlowPointIndex, f3NetFpQosPolicerIndex, f3NetFpQosPolicerStatsIndex }
    ::= { f3NetFpQosPolicerStatsTable 1 }

F3NetFpQosPolicerStatsEntry ::= SEQUENCE {
    f3NetFpQosPolicerStatsIndex           Integer32,
    f3NetFpQosPolicerStatsIntervalType    CmPmIntervalType,
    f3NetFpQosPolicerStatsValid           TruthValue,
    f3NetFpQosPolicerStatsAction          CmPmBinAction,
    f3NetFpQosPolicerStatsFMG             PerfCounter64,
    f3NetFpQosPolicerStatsFMY             PerfCounter64,
    f3NetFpQosPolicerStatsFMRD            PerfCounter64,
    f3NetFpQosPolicerStatsBytesIn         PerfCounter64,
    f3NetFpQosPolicerStatsBytesOut        PerfCounter64,
    f3NetFpQosPolicerStatsABR             PerfCounter64
}

f3NetFpQosPolicerStatsIndex OBJECT-TYPE
    SYNTAX      Integer32 (1..65535)
    MAX-ACCESS  read-only
    STATUS      current
    DESCRIPTION
            "An integer index value used to uniquely identify
            this QOS Policer statistics entry.
            1 - 15min
            2 - 1day
            3 - rollover
            4 - 5min"
    ::= { f3NetFpQosPolicerStatsEntry 1 }

f3NetFpQosPolicerStatsIntervalType OBJECT-TYPE
    SYNTAX      CmPmIntervalType
    MAX-ACCESS  read-only
    STATUS      current
    DESCRIPTION
            "Interval over which Performance Monitoring data is collected."
    ::= { f3NetFpQosPolicerStatsEntry 2 }

f3NetFpQosPolicerStatsValid OBJECT-TYPE
    SYNTAX      TruthValue
    MAX-ACCESS  read-only
    STATUS      current
    DESCRIPTION
            "Indicates the validity of the bin."
    ::= { f3NetFpQosPolicerStatsEntry 3 }

f3NetFpQosPolicerStatsAction OBJECT-TYPE
    SYNTAX      CmPmBinAction
    MAX-ACCESS  read-write
    STATUS      current
    DESCRIPTION
            "Allows the Manager to clear the bin."
    ::= { f3NetFpQosPolicerStatsEntry 4 }

f3NetFpQosPolicerStatsFMG OBJECT-TYPE
     SYNTAX     PerfCounter64
     MAX-ACCESS read-only
     STATUS     current
     DESCRIPTION
         "Frames Marked Green."
     ::= { f3NetFpQosPolicerStatsEntry 5 }

f3NetFpQosPolicerStatsFMY OBJECT-TYPE
     SYNTAX     PerfCounter64
     MAX-ACCESS read-only
     STATUS     current
     DESCRIPTION
         "Frames Marked Yellow."
     ::= { f3NetFpQosPolicerStatsEntry 6 }

f3NetFpQosPolicerStatsFMRD OBJECT-TYPE
     SYNTAX     PerfCounter64
     MAX-ACCESS read-only
     STATUS     current
     DESCRIPTION
         "Frames Marked Red and Discarded."
     ::= { f3NetFpQosPolicerStatsEntry 7 }

f3NetFpQosPolicerStatsBytesIn OBJECT-TYPE
     SYNTAX     PerfCounter64
     MAX-ACCESS read-only
     STATUS     current
     DESCRIPTION
         "Number of bytes received by the Policer."
     ::= { f3NetFpQosPolicerStatsEntry 8 }

f3NetFpQosPolicerStatsBytesOut OBJECT-TYPE
     SYNTAX     PerfCounter64
     MAX-ACCESS read-only
     STATUS     current
     DESCRIPTION
         "Number of bytes transmitted by the Policer."
     ::= { f3NetFpQosPolicerStatsEntry 9 }

f3NetFpQosPolicerStatsABR OBJECT-TYPE
     SYNTAX     PerfCounter64
     MAX-ACCESS read-only
     STATUS     current
     DESCRIPTION
         "Average Bit Rate  on the Policer."
     ::= { f3NetFpQosPolicerStatsEntry 10 }

--
-- Network Flow Point QoS Policer History Statistics Table
--

f3NetFpQosPolicerHistoryTable OBJECT-TYPE
    SYNTAX      SEQUENCE OF F3NetFpQosPolicerHistoryEntry
    MAX-ACCESS  not-accessible
    STATUS      current
    DESCRIPTION
            "A collection of Net FlowPoint QOS Policer statistics.  
             These reflect the history data."
    ::= { f3FpmPerfObjects 20 }

f3NetFpQosPolicerHistoryEntry OBJECT-TYPE
    SYNTAX      F3NetFpQosPolicerHistoryEntry 
    MAX-ACCESS  not-accessible
    STATUS      current
    DESCRIPTION
            "A conceptual row in the f3NetFpQosPolicerHistoryTable.
             Entries exist in this table for each Net FlowPoint QoS Policer."
    INDEX { neIndex, shelfIndex, slotIndex, cmEthernetNetPortIndex, 
            f3NetFlowPointIndex, f3NetFpQosPolicerIndex, 
            f3NetFpQosPolicerStatsIndex, f3NetFpQosPolicerHistoryIndex }
    ::= { f3NetFpQosPolicerHistoryTable 1 }

F3NetFpQosPolicerHistoryEntry ::= SEQUENCE {
    f3NetFpQosPolicerHistoryIndex           Integer32,
    f3NetFpQosPolicerHistoryTime            DateAndTime,
    f3NetFpQosPolicerHistoryValid           TruthValue,
    f3NetFpQosPolicerHistoryAction          CmPmBinAction,
    f3NetFpQosPolicerHistoryFMG             PerfCounter64,
    f3NetFpQosPolicerHistoryFMY             PerfCounter64,
    f3NetFpQosPolicerHistoryFMRD            PerfCounter64,
    f3NetFpQosPolicerHistoryBytesIn         PerfCounter64,
    f3NetFpQosPolicerHistoryBytesOut        PerfCounter64,
    f3NetFpQosPolicerHistoryABR             PerfCounter64
}

f3NetFpQosPolicerHistoryIndex OBJECT-TYPE
    SYNTAX      Integer32 (1..65535)
    MAX-ACCESS  read-only
    STATUS      current
    DESCRIPTION
            "An arbitrary integer index value used to uniquely identify
            this QOS Policer history entry."
    ::= { f3NetFpQosPolicerHistoryEntry 1 }

f3NetFpQosPolicerHistoryTime OBJECT-TYPE
    SYNTAX      DateAndTime
    MAX-ACCESS  read-only
    STATUS      current
    DESCRIPTION
            "Indicates the time of history bin creation." 
    ::= { f3NetFpQosPolicerHistoryEntry 2 }

f3NetFpQosPolicerHistoryValid OBJECT-TYPE
    SYNTAX      TruthValue
    MAX-ACCESS  read-only
    STATUS      current
    DESCRIPTION
            "Indicates the validity of the bin."
    ::= { f3NetFpQosPolicerHistoryEntry 3 }

f3NetFpQosPolicerHistoryAction OBJECT-TYPE
    SYNTAX      CmPmBinAction
    MAX-ACCESS  read-write
    STATUS      current
    DESCRIPTION
            "Allows the Manager to clear the bin."
    ::= { f3NetFpQosPolicerHistoryEntry 4 }

f3NetFpQosPolicerHistoryFMG OBJECT-TYPE
     SYNTAX     PerfCounter64
     MAX-ACCESS read-only
     STATUS     current
     DESCRIPTION
         "Frames Marked Green."
     ::= { f3NetFpQosPolicerHistoryEntry 5 }

f3NetFpQosPolicerHistoryFMY OBJECT-TYPE
     SYNTAX     PerfCounter64
     MAX-ACCESS read-only
     STATUS     current
     DESCRIPTION
         "Frames Marked Yellow."
     ::= { f3NetFpQosPolicerHistoryEntry 6 }

f3NetFpQosPolicerHistoryFMRD OBJECT-TYPE
     SYNTAX     PerfCounter64
     MAX-ACCESS read-only
     STATUS     current
     DESCRIPTION
         "Frames Marked Red and Discarded."
     ::= { f3NetFpQosPolicerHistoryEntry 7 }

f3NetFpQosPolicerHistoryBytesIn OBJECT-TYPE
     SYNTAX     PerfCounter64
     MAX-ACCESS read-only
     STATUS     current
     DESCRIPTION
         "Number of bytes received by the Policer."
     ::= { f3NetFpQosPolicerHistoryEntry 8 }

f3NetFpQosPolicerHistoryBytesOut OBJECT-TYPE
     SYNTAX     PerfCounter64
     MAX-ACCESS read-only
     STATUS     current
     DESCRIPTION
         "Number of bytes transmitted by the Policer."
     ::= { f3NetFpQosPolicerHistoryEntry 9 }

f3NetFpQosPolicerHistoryABR OBJECT-TYPE
     SYNTAX     PerfCounter64
     MAX-ACCESS read-only
     STATUS     current
     DESCRIPTION
         "Average Bit Rate  on the Policer."
     ::= { f3NetFpQosPolicerHistoryEntry 10 }

--
-- Network Flow Point QoS Policer Threshold Table
--

f3NetFpQosPolicerThresholdTable OBJECT-TYPE
    SYNTAX      SEQUENCE OF F3NetFpQosPolicerThresholdEntry
    MAX-ACCESS  not-accessible
    STATUS      current
    DESCRIPTION
            "A table of entries that allow manageability of QOS
             Policer Thresholds."
    ::= { f3FpmPerfObjects 21 }

f3NetFpQosPolicerThresholdEntry OBJECT-TYPE
    SYNTAX      F3NetFpQosPolicerThresholdEntry
    MAX-ACCESS  not-accessible
    STATUS      current
    DESCRIPTION
            "A conceptual row in the f3NetFpQosPolicerThresholdTable."
    INDEX { neIndex, shelfIndex, slotIndex, cmEthernetNetPortIndex, 
            f3NetFlowPointIndex, f3NetFpQosPolicerIndex, 
            f3NetFpQosPolicerStatsIndex, f3NetFpQosPolicerThresholdIndex }
    ::= { f3NetFpQosPolicerThresholdTable 1 }

F3NetFpQosPolicerThresholdEntry ::= SEQUENCE {
    f3NetFpQosPolicerThresholdIndex       Integer32,
    f3NetFpQosPolicerThresholdInterval    CmPmIntervalType,
    f3NetFpQosPolicerThresholdVariable    VariablePointer,
    f3NetFpQosPolicerThresholdValueLo     Unsigned32,
    f3NetFpQosPolicerThresholdValueHi     Unsigned32,
    f3NetFpQosPolicerThresholdMonValue    Counter64
}

f3NetFpQosPolicerThresholdIndex OBJECT-TYPE
    SYNTAX     Integer32 (1..65535)
    MAX-ACCESS read-only
    STATUS     current
    DESCRIPTION
        "An index that uniquely identifies an entry in the
         f3NetFpQosPolicerThresholdTable."
    ::= { f3NetFpQosPolicerThresholdEntry 1 }

f3NetFpQosPolicerThresholdInterval OBJECT-TYPE
    SYNTAX     CmPmIntervalType
    MAX-ACCESS read-only
    STATUS     current
    DESCRIPTION
        "The interval over which monitored value is
         sampled and compared with the specified threshold."
    ::= { f3NetFpQosPolicerThresholdEntry 2 }

f3NetFpQosPolicerThresholdVariable OBJECT-TYPE
    SYNTAX     VariablePointer
    MAX-ACCESS read-only
    STATUS     current
    DESCRIPTION
        "The object identifier of the particular variable to be
         sampled."
    ::= { f3NetFpQosPolicerThresholdEntry 3 }

f3NetFpQosPolicerThresholdValueLo OBJECT-TYPE
    SYNTAX     Unsigned32
    MAX-ACCESS read-write
    STATUS     current
    DESCRIPTION
        "Lower 32 bits of the threshold value."
    ::= { f3NetFpQosPolicerThresholdEntry 4 }

f3NetFpQosPolicerThresholdValueHi OBJECT-TYPE
    SYNTAX     Unsigned32
    MAX-ACCESS read-write
    STATUS     current
    DESCRIPTION
        "Higher 32 bits of the threshold value."
    ::= { f3NetFpQosPolicerThresholdEntry 5 }

f3NetFpQosPolicerThresholdMonValue OBJECT-TYPE
    SYNTAX     Counter64
    MAX-ACCESS read-only
    STATUS     current
    DESCRIPTION
        "Monitored value corresponding to f3NetFpQosPolicerThresholdVariable."
    ::= { f3NetFpQosPolicerThresholdEntry 6 }

--
-- FPM Access Port Shaper Current Statistics Table
--

f3AccPortFpQosShaperStatsTable OBJECT-TYPE
    SYNTAX      SEQUENCE OF F3AccPortFpQosShaperStatsEntry
    MAX-ACCESS  not-accessible
    STATUS      current
    DESCRIPTION
            "A collection of Acc Port QOS Shaper statistics.  
             These reflect the current data."
    ::= { f3FpmPerfObjects 22 }

f3AccPortFpQosShaperStatsEntry OBJECT-TYPE
    SYNTAX      F3AccPortFpQosShaperStatsEntry 
    MAX-ACCESS  not-accessible
    STATUS      current
    DESCRIPTION
            "A conceptual row in the f3AccPortFpQosShaperStatsTable.
             Entries exist in this table for each Port QoS Shaper."
    INDEX { neIndex, shelfIndex, slotIndex, cmEthernetAccPortIndex,
            f3AccPortFpQosShaperIndex, f3AccPortFpQosShaperStatsIndex }
    ::= { f3AccPortFpQosShaperStatsTable 1 }

F3AccPortFpQosShaperStatsEntry ::= SEQUENCE {
    f3AccPortFpQosShaperStatsIndex             Integer32,
    f3AccPortFpQosShaperStatsIntervalType      CmPmIntervalType,
    f3AccPortFpQosShaperStatsValid             TruthValue,
    f3AccPortFpQosShaperStatsAction            CmPmBinAction,
    f3AccPortFpQosShaperStatsBT                PerfCounter64,
    f3AccPortFpQosShaperStatsBTD               PerfCounter64,
    f3AccPortFpQosShaperStatsFD                PerfCounter64,
    f3AccPortFpQosShaperStatsFTD               PerfCounter64,
    f3AccPortFpQosShaperStatsABRRL             PerfCounter64,
    f3AccPortFpQosShaperStatsBREDD             PerfCounter64,
    f3AccPortFpQosShaperStatsFREDD             PerfCounter64
}

f3AccPortFpQosShaperStatsIndex OBJECT-TYPE
    SYNTAX      Integer32 (1..65535)
    MAX-ACCESS  read-only
    STATUS      current
    DESCRIPTION
            "An arbitrary integer index value used to uniquely identify
            this QOS Shaper statistics entry.
            1 - 15min
            2 - 1day
            3 - rollover
            4 - 5min"
    ::= { f3AccPortFpQosShaperStatsEntry 1 }

f3AccPortFpQosShaperStatsIntervalType OBJECT-TYPE
    SYNTAX      CmPmIntervalType
    MAX-ACCESS  read-only
    STATUS      current
    DESCRIPTION
            "Interval over which Performance Monitoring data is collected."
    ::= { f3AccPortFpQosShaperStatsEntry 2 }

f3AccPortFpQosShaperStatsValid OBJECT-TYPE
    SYNTAX      TruthValue
    MAX-ACCESS  read-only
    STATUS      current
    DESCRIPTION
            "Indicates the validity of the bin."
    ::= { f3AccPortFpQosShaperStatsEntry 3 }

f3AccPortFpQosShaperStatsAction OBJECT-TYPE
    SYNTAX      CmPmBinAction
    MAX-ACCESS  read-write
    STATUS      current
    DESCRIPTION
            "Allows the Manager to clear the bin."
    ::= { f3AccPortFpQosShaperStatsEntry 4 }

f3AccPortFpQosShaperStatsBT OBJECT-TYPE
     SYNTAX     PerfCounter64
     MAX-ACCESS read-only
     STATUS     current
     DESCRIPTION
         "Bytes Transmitted."
     ::= { f3AccPortFpQosShaperStatsEntry 5 }

f3AccPortFpQosShaperStatsBTD OBJECT-TYPE
     SYNTAX     PerfCounter64
     MAX-ACCESS read-only
     STATUS     current
     DESCRIPTION
         "Bytes Tail Dropped."
     ::= { f3AccPortFpQosShaperStatsEntry 6 }

f3AccPortFpQosShaperStatsFD OBJECT-TYPE
     SYNTAX     PerfCounter64
     MAX-ACCESS read-only
     STATUS     current
     DESCRIPTION
         "Frames Dequeued."
     ::= { f3AccPortFpQosShaperStatsEntry 7 }

f3AccPortFpQosShaperStatsFTD OBJECT-TYPE
     SYNTAX     PerfCounter64
     MAX-ACCESS read-only
     STATUS     current
     DESCRIPTION
         "Frames Tail Dropped."
     ::= { f3AccPortFpQosShaperStatsEntry 8 }

f3AccPortFpQosShaperStatsABRRL OBJECT-TYPE
     SYNTAX     PerfCounter64
     MAX-ACCESS read-only
     STATUS     current
     DESCRIPTION
         "Average Bit Rate - Rate Limited."
     ::= { f3AccPortFpQosShaperStatsEntry 9 }

f3AccPortFpQosShaperStatsBREDD OBJECT-TYPE
     SYNTAX     PerfCounter64
     MAX-ACCESS read-only
     STATUS     current
     DESCRIPTION
         "Bytes Random Early Discard, Dropped."
     ::= { f3AccPortFpQosShaperStatsEntry 10 }

f3AccPortFpQosShaperStatsFREDD OBJECT-TYPE
     SYNTAX     PerfCounter64
     MAX-ACCESS read-only
     STATUS     current
     DESCRIPTION
         "Frames Random Early Discard, Dropped."
     ::= { f3AccPortFpQosShaperStatsEntry 11 }

--
-- FPM Access Port QoS Shaper History Statistics Table
--

f3AccPortFpQosShaperHistoryTable OBJECT-TYPE
    SYNTAX      SEQUENCE OF F3AccPortFpQosShaperHistoryEntry
    MAX-ACCESS  not-accessible
    STATUS      current
    DESCRIPTION
            "A collection of Acc Port QOS Shaper statistics.  
             These reflect the history data."
    ::= { f3FpmPerfObjects 23 }

f3AccPortFpQosShaperHistoryEntry OBJECT-TYPE
    SYNTAX      F3AccPortFpQosShaperHistoryEntry 
    MAX-ACCESS  not-accessible
    STATUS      current
    DESCRIPTION
            "A conceptual row in the f3AccPortFpQosShaperHistoryTable.
             Entries exist in this table for each Port QoS Shaper."
    INDEX { neIndex, shelfIndex, slotIndex, cmEthernetAccPortIndex,
            f3AccPortFpQosShaperIndex, f3AccPortFpQosShaperStatsIndex, 
            f3AccPortFpQosShaperHistoryIndex }
    ::= { f3AccPortFpQosShaperHistoryTable 1 }

F3AccPortFpQosShaperHistoryEntry ::= SEQUENCE {
    f3AccPortFpQosShaperHistoryIndex             Integer32,
    f3AccPortFpQosShaperHistoryTime              DateAndTime,
    f3AccPortFpQosShaperHistoryValid             TruthValue,
    f3AccPortFpQosShaperHistoryAction            CmPmBinAction,
    f3AccPortFpQosShaperHistoryBT                PerfCounter64,
    f3AccPortFpQosShaperHistoryBTD               PerfCounter64,
    f3AccPortFpQosShaperHistoryFD                PerfCounter64,
    f3AccPortFpQosShaperHistoryFTD               PerfCounter64,
    f3AccPortFpQosShaperHistoryABRRL             PerfCounter64,
    f3AccPortFpQosShaperHistoryBREDD             PerfCounter64,
    f3AccPortFpQosShaperHistoryFREDD             PerfCounter64
}

f3AccPortFpQosShaperHistoryIndex OBJECT-TYPE
    SYNTAX      Integer32 (1..65535)
    MAX-ACCESS  read-only
    STATUS      current
    DESCRIPTION
            "An arbitrary integer index value used to uniquely identify
            this QOS Shaper statistics entry."
    ::= { f3AccPortFpQosShaperHistoryEntry 1 }

f3AccPortFpQosShaperHistoryTime OBJECT-TYPE
    SYNTAX      DateAndTime
    MAX-ACCESS  read-only
    STATUS      current
    DESCRIPTION
            "Indicates the time of history bin creation." 
    ::= { f3AccPortFpQosShaperHistoryEntry 2 }

f3AccPortFpQosShaperHistoryValid OBJECT-TYPE
    SYNTAX      TruthValue
    MAX-ACCESS  read-only
    STATUS      current
    DESCRIPTION
            "Indicates the validity of the bin."
    ::= { f3AccPortFpQosShaperHistoryEntry 3 }

f3AccPortFpQosShaperHistoryAction OBJECT-TYPE
    SYNTAX      CmPmBinAction
    MAX-ACCESS  read-write
    STATUS      current
    DESCRIPTION
            "Allows the Manager to clear the bin."
    ::= { f3AccPortFpQosShaperHistoryEntry 4 }

f3AccPortFpQosShaperHistoryBT OBJECT-TYPE
     SYNTAX     PerfCounter64
     MAX-ACCESS read-only
     STATUS     current
     DESCRIPTION
         "Bytes Transmitted."
     ::= { f3AccPortFpQosShaperHistoryEntry 5 }

f3AccPortFpQosShaperHistoryBTD OBJECT-TYPE
     SYNTAX     PerfCounter64
     MAX-ACCESS read-only
     STATUS     current
     DESCRIPTION
         "Bytes Tail Dropped."
     ::= { f3AccPortFpQosShaperHistoryEntry 6 }

f3AccPortFpQosShaperHistoryFD OBJECT-TYPE
     SYNTAX     PerfCounter64
     MAX-ACCESS read-only
     STATUS     current
     DESCRIPTION
         "Frames Dequeued."
     ::= { f3AccPortFpQosShaperHistoryEntry 7 }

f3AccPortFpQosShaperHistoryFTD OBJECT-TYPE
     SYNTAX     PerfCounter64
     MAX-ACCESS read-only
     STATUS     current
     DESCRIPTION
         "Frames Tail Dropped."
     ::= { f3AccPortFpQosShaperHistoryEntry 8 }

f3AccPortFpQosShaperHistoryABRRL OBJECT-TYPE
     SYNTAX     PerfCounter64
     MAX-ACCESS read-only
     STATUS     current
     DESCRIPTION
         "Average Bit Rate - Rate Limited."
     ::= { f3AccPortFpQosShaperHistoryEntry 9 }

f3AccPortFpQosShaperHistoryBREDD OBJECT-TYPE
     SYNTAX     PerfCounter64
     MAX-ACCESS read-only
     STATUS     current
     DESCRIPTION
         "Bytes Random Early Discard, Dropped."
     ::= { f3AccPortFpQosShaperHistoryEntry 10 }

f3AccPortFpQosShaperHistoryFREDD OBJECT-TYPE
     SYNTAX     PerfCounter64
     MAX-ACCESS read-only
     STATUS     current
     DESCRIPTION
         "Frames Random Early Discard, Dropped."
     ::= { f3AccPortFpQosShaperHistoryEntry 11 }

--
-- FPM Access Port QoS Shaper Threshold Table
--

f3AccPortFpQosShaperThresholdTable OBJECT-TYPE
    SYNTAX      SEQUENCE OF F3AccPortFpQosShaperThresholdEntry
    MAX-ACCESS  not-accessible
    STATUS      current
    DESCRIPTION
            "A table of entries that allow manageability of Acc Port
             QoS Shaper Thresholds."
    ::= { f3FpmPerfObjects 24 }

f3AccPortFpQosShaperThresholdEntry OBJECT-TYPE
    SYNTAX      F3AccPortFpQosShaperThresholdEntry
    MAX-ACCESS  not-accessible
    STATUS      current
    DESCRIPTION
            "A conceptual row in the f3AccPortFpQosShaperThresholdTable."
    INDEX { neIndex, shelfIndex, slotIndex, cmEthernetAccPortIndex,
            f3AccPortFpQosShaperIndex, f3AccPortFpQosShaperStatsIndex, 
            f3AccPortFpQosShaperThresholdIndex }
    ::= { f3AccPortFpQosShaperThresholdTable 1 }

F3AccPortFpQosShaperThresholdEntry ::= SEQUENCE {
    f3AccPortFpQosShaperThresholdIndex       Integer32,
    f3AccPortFpQosShaperThresholdInterval    CmPmIntervalType,
    f3AccPortFpQosShaperThresholdVariable    VariablePointer,
    f3AccPortFpQosShaperThresholdValueLo     Unsigned32,
    f3AccPortFpQosShaperThresholdValueHi     Unsigned32,
    f3AccPortFpQosShaperThresholdMonValue    Counter64
}

f3AccPortFpQosShaperThresholdIndex OBJECT-TYPE
    SYNTAX     Integer32 (1..65535)
    MAX-ACCESS read-only
    STATUS     current
    DESCRIPTION
        "An index that uniquely identifies an entry in the
        f3AccPortFpQosShaperThresholdTable."
    ::= { f3AccPortFpQosShaperThresholdEntry 1 }

f3AccPortFpQosShaperThresholdInterval OBJECT-TYPE
    SYNTAX     CmPmIntervalType
    MAX-ACCESS read-only
    STATUS     current
    DESCRIPTION
        "The interval over which monitored value is
        sampled and compared with the specified threshold."
    ::= { f3AccPortFpQosShaperThresholdEntry 2 }

f3AccPortFpQosShaperThresholdVariable OBJECT-TYPE
    SYNTAX     VariablePointer
    MAX-ACCESS read-only
    STATUS     current
    DESCRIPTION
        "The object identifier of the particular variable to be
        sampled."
    ::= { f3AccPortFpQosShaperThresholdEntry 3 }

f3AccPortFpQosShaperThresholdValueLo OBJECT-TYPE
    SYNTAX     Unsigned32
    MAX-ACCESS read-write
    STATUS     current
    DESCRIPTION
        "Lower 32 bits of the threshold value."
    ::= { f3AccPortFpQosShaperThresholdEntry 4 }

f3AccPortFpQosShaperThresholdValueHi OBJECT-TYPE
    SYNTAX     Unsigned32
    MAX-ACCESS read-write
    STATUS     current
    DESCRIPTION
        "Higher 32 bits of the threshold value."
    ::= { f3AccPortFpQosShaperThresholdEntry 5 }

f3AccPortFpQosShaperThresholdMonValue OBJECT-TYPE
    SYNTAX     Counter64
    MAX-ACCESS read-only
    STATUS     current
    DESCRIPTION
        "Monitored value corresponding to f3AccPortFpQosShaperThresholdVariable."
    ::= { f3AccPortFpQosShaperThresholdEntry 6 }

--
-- FPM Network Port QoS Shaper Current Statistics Table
--

f3NetPortFpQosShaperStatsTable OBJECT-TYPE
    SYNTAX      SEQUENCE OF F3NetPortFpQosShaperStatsEntry
    MAX-ACCESS  not-accessible
    STATUS      current
    DESCRIPTION
            "A collection of Net Port QOS Shaper statistics.  
             These reflect the current data."
    ::= { f3FpmPerfObjects 25 }

f3NetPortFpQosShaperStatsEntry OBJECT-TYPE
    SYNTAX      F3NetPortFpQosShaperStatsEntry 
    MAX-ACCESS  not-accessible
    STATUS      current
    DESCRIPTION
            "A conceptual row in the f3NetPortFpQosShaperStatsTable.
             Entries exist in this table for each Port QoS Shaper."
    INDEX { neIndex, shelfIndex, slotIndex, cmEthernetNetPortIndex,
            f3NetPortFpQosShaperIndex, f3NetPortFpQosShaperStatsIndex }
    ::= { f3NetPortFpQosShaperStatsTable 1 }

F3NetPortFpQosShaperStatsEntry ::= SEQUENCE {
    f3NetPortFpQosShaperStatsIndex             Integer32,
    f3NetPortFpQosShaperStatsIntervalType      CmPmIntervalType,
    f3NetPortFpQosShaperStatsValid             TruthValue,
    f3NetPortFpQosShaperStatsAction            CmPmBinAction,
    f3NetPortFpQosShaperStatsBT                PerfCounter64,
    f3NetPortFpQosShaperStatsBTD               PerfCounter64,
    f3NetPortFpQosShaperStatsFD                PerfCounter64,
    f3NetPortFpQosShaperStatsFTD               PerfCounter64,
    f3NetPortFpQosShaperStatsABRRL             PerfCounter64,
    f3NetPortFpQosShaperStatsBREDD             PerfCounter64,
    f3NetPortFpQosShaperStatsFREDD             PerfCounter64
}

f3NetPortFpQosShaperStatsIndex OBJECT-TYPE
    SYNTAX      Integer32 (1..65535)
    MAX-ACCESS  read-only
    STATUS      current
    DESCRIPTION
            "An arbitrary integer index value used to uniquely identify
            this QOS Shaper statistics entry.
            1 - 15min
            2 - 1day
            3 - rollover
            4 - 5min"
    ::= { f3NetPortFpQosShaperStatsEntry 1 }

f3NetPortFpQosShaperStatsIntervalType OBJECT-TYPE
    SYNTAX      CmPmIntervalType
    MAX-ACCESS  read-only
    STATUS      current
    DESCRIPTION
            "Interval over which Performance Monitoring data is collected."
    ::= { f3NetPortFpQosShaperStatsEntry 2 }

f3NetPortFpQosShaperStatsValid OBJECT-TYPE
    SYNTAX      TruthValue
    MAX-ACCESS  read-only
    STATUS      current
    DESCRIPTION
            "Indicates the validity of the bin."
    ::= { f3NetPortFpQosShaperStatsEntry 3 }

f3NetPortFpQosShaperStatsAction OBJECT-TYPE
    SYNTAX      CmPmBinAction
    MAX-ACCESS  read-write
    STATUS      current
    DESCRIPTION
            "Allows the Manager to clear the bin."
    ::= { f3NetPortFpQosShaperStatsEntry 4 }

f3NetPortFpQosShaperStatsBT OBJECT-TYPE
     SYNTAX     PerfCounter64
     MAX-ACCESS read-only
     STATUS     current
     DESCRIPTION
         "Bytes Transmitted."
     ::= { f3NetPortFpQosShaperStatsEntry 5 }

f3NetPortFpQosShaperStatsBTD OBJECT-TYPE
     SYNTAX     PerfCounter64
     MAX-ACCESS read-only
     STATUS     current
     DESCRIPTION
         "Bytes Tail Dropped."
     ::= { f3NetPortFpQosShaperStatsEntry 6 }

f3NetPortFpQosShaperStatsFD OBJECT-TYPE
     SYNTAX     PerfCounter64
     MAX-ACCESS read-only
     STATUS     current
     DESCRIPTION
         "Frames Dequeued."
     ::= { f3NetPortFpQosShaperStatsEntry 7 }

f3NetPortFpQosShaperStatsFTD OBJECT-TYPE
     SYNTAX     PerfCounter64
     MAX-ACCESS read-only
     STATUS     current
     DESCRIPTION
         "Frames Tail Dropped."
     ::= { f3NetPortFpQosShaperStatsEntry 8 }

f3NetPortFpQosShaperStatsABRRL OBJECT-TYPE
     SYNTAX     PerfCounter64
     MAX-ACCESS read-only
     STATUS     current
     DESCRIPTION
         "Average Bit Rate - Rate Limited."
     ::= { f3NetPortFpQosShaperStatsEntry 9 }

f3NetPortFpQosShaperStatsBREDD OBJECT-TYPE
     SYNTAX     PerfCounter64
     MAX-ACCESS read-only
     STATUS     current
     DESCRIPTION
         "Bytes Random Early Discard, Dropped."
     ::= { f3NetPortFpQosShaperStatsEntry 10 }

f3NetPortFpQosShaperStatsFREDD OBJECT-TYPE
     SYNTAX     PerfCounter64
     MAX-ACCESS read-only
     STATUS     current
     DESCRIPTION
         "Frames Random Early Discard, Dropped."
     ::= { f3NetPortFpQosShaperStatsEntry 11 }

--
-- FPM Network Port QoS Shaper History Statistics Table
--

f3NetPortFpQosShaperHistoryTable OBJECT-TYPE
    SYNTAX      SEQUENCE OF F3NetPortFpQosShaperHistoryEntry
    MAX-ACCESS  not-accessible
    STATUS      current
    DESCRIPTION
            "A collection of Net Port QOS Shaper statistics.  
             These reflect the history data."
    ::= { f3FpmPerfObjects 26 }

f3NetPortFpQosShaperHistoryEntry OBJECT-TYPE
    SYNTAX      F3NetPortFpQosShaperHistoryEntry 
    MAX-ACCESS  not-accessible
    STATUS      current
    DESCRIPTION
            "A conceptual row in the f3NetPortFpQosShaperHistoryTable.
             Entries exist in this table for each Port QoS Shaper."
    INDEX { neIndex, shelfIndex, slotIndex, cmEthernetNetPortIndex,
            f3NetPortFpQosShaperIndex, f3NetPortFpQosShaperStatsIndex, 
            f3NetPortFpQosShaperHistoryIndex }
    ::= { f3NetPortFpQosShaperHistoryTable 1 }

F3NetPortFpQosShaperHistoryEntry ::= SEQUENCE {
    f3NetPortFpQosShaperHistoryIndex             Integer32,
    f3NetPortFpQosShaperHistoryTime              DateAndTime,
    f3NetPortFpQosShaperHistoryValid             TruthValue,
    f3NetPortFpQosShaperHistoryAction            CmPmBinAction,
    f3NetPortFpQosShaperHistoryBT                PerfCounter64,
    f3NetPortFpQosShaperHistoryBTD               PerfCounter64,
    f3NetPortFpQosShaperHistoryFD                PerfCounter64,
    f3NetPortFpQosShaperHistoryFTD               PerfCounter64,
    f3NetPortFpQosShaperHistoryABRRL             PerfCounter64,
    f3NetPortFpQosShaperHistoryBREDD             PerfCounter64,
    f3NetPortFpQosShaperHistoryFREDD             PerfCounter64
}

f3NetPortFpQosShaperHistoryIndex OBJECT-TYPE
    SYNTAX      Integer32 (1..65535)
    MAX-ACCESS  read-only
    STATUS      current
    DESCRIPTION
            "An arbitrary integer index value used to uniquely identify
            this QOS Shaper statistics entry."
    ::= { f3NetPortFpQosShaperHistoryEntry 1 }

f3NetPortFpQosShaperHistoryTime OBJECT-TYPE
    SYNTAX      DateAndTime
    MAX-ACCESS  read-only
    STATUS      current
    DESCRIPTION
            "Indicates the time of history bin creation." 
    ::= { f3NetPortFpQosShaperHistoryEntry 2 }

f3NetPortFpQosShaperHistoryValid OBJECT-TYPE
    SYNTAX      TruthValue
    MAX-ACCESS  read-only
    STATUS      current
    DESCRIPTION
            "Indicates the validity of the bin."
    ::= { f3NetPortFpQosShaperHistoryEntry 3 }

f3NetPortFpQosShaperHistoryAction OBJECT-TYPE
    SYNTAX      CmPmBinAction
    MAX-ACCESS  read-write
    STATUS      current
    DESCRIPTION
            "Allows the Manager to clear the bin."
    ::= { f3NetPortFpQosShaperHistoryEntry 4 }

f3NetPortFpQosShaperHistoryBT OBJECT-TYPE
     SYNTAX     PerfCounter64
     MAX-ACCESS read-only
     STATUS     current
     DESCRIPTION
         "Bytes Transmitted."
     ::= { f3NetPortFpQosShaperHistoryEntry 5 }

f3NetPortFpQosShaperHistoryBTD OBJECT-TYPE
     SYNTAX     PerfCounter64
     MAX-ACCESS read-only
     STATUS     current
     DESCRIPTION
         "Bytes Tail Dropped."
     ::= { f3NetPortFpQosShaperHistoryEntry 6 }

f3NetPortFpQosShaperHistoryFD OBJECT-TYPE
     SYNTAX     PerfCounter64
     MAX-ACCESS read-only
     STATUS     current
     DESCRIPTION
         "Frames Dequeued."
     ::= { f3NetPortFpQosShaperHistoryEntry 7 }

f3NetPortFpQosShaperHistoryFTD OBJECT-TYPE
     SYNTAX     PerfCounter64
     MAX-ACCESS read-only
     STATUS     current
     DESCRIPTION
         "Frames Tail Dropped."
     ::= { f3NetPortFpQosShaperHistoryEntry 8 }

f3NetPortFpQosShaperHistoryABRRL OBJECT-TYPE
     SYNTAX     PerfCounter64
     MAX-ACCESS read-only
     STATUS     current
     DESCRIPTION
         "Average Bit Rate - Rate Limited."
     ::= { f3NetPortFpQosShaperHistoryEntry 9 }

f3NetPortFpQosShaperHistoryBREDD OBJECT-TYPE
     SYNTAX     PerfCounter64
     MAX-ACCESS read-only
     STATUS     current
     DESCRIPTION
         "Bytes Random Early Discard, Dropped."
     ::= { f3NetPortFpQosShaperHistoryEntry 10 }

f3NetPortFpQosShaperHistoryFREDD OBJECT-TYPE
     SYNTAX     PerfCounter64
     MAX-ACCESS read-only
     STATUS     current
     DESCRIPTION
         "Frames Random Early Discard, Dropped."
     ::= { f3NetPortFpQosShaperHistoryEntry 11 }

--
-- FPM Network Port QoS Shaper Threshold Table
--

f3NetPortFpQosShaperThresholdTable OBJECT-TYPE
    SYNTAX      SEQUENCE OF F3NetPortFpQosShaperThresholdEntry
    MAX-ACCESS  not-accessible
    STATUS      current
    DESCRIPTION
            "A table of entries that allow manageability of Net Port
             QoS Shaper Thresholds."
    ::= { f3FpmPerfObjects 27 }

f3NetPortFpQosShaperThresholdEntry OBJECT-TYPE
    SYNTAX      F3NetPortFpQosShaperThresholdEntry
    MAX-ACCESS  not-accessible
    STATUS      current
    DESCRIPTION
            "A conceptual row in the f3NetPortFpQosShaperThresholdTable."
    INDEX { neIndex, shelfIndex, slotIndex, cmEthernetNetPortIndex,
            f3NetPortFpQosShaperIndex, f3NetPortFpQosShaperStatsIndex, 
            f3NetPortFpQosShaperThresholdIndex }
    ::= { f3NetPortFpQosShaperThresholdTable 1 }

F3NetPortFpQosShaperThresholdEntry ::= SEQUENCE {
    f3NetPortFpQosShaperThresholdIndex       Integer32,
    f3NetPortFpQosShaperThresholdInterval    CmPmIntervalType,
    f3NetPortFpQosShaperThresholdVariable    VariablePointer,
    f3NetPortFpQosShaperThresholdValueLo     Unsigned32,
    f3NetPortFpQosShaperThresholdValueHi     Unsigned32,
    f3NetPortFpQosShaperThresholdMonValue    Counter64
}

f3NetPortFpQosShaperThresholdIndex OBJECT-TYPE
    SYNTAX     Integer32 (1..65535)
    MAX-ACCESS read-only
    STATUS     current
    DESCRIPTION
        "An index that uniquely identifies an entry in the
        f3NetPortFpQosShaperThresholdTable."
    ::= { f3NetPortFpQosShaperThresholdEntry 1 }

f3NetPortFpQosShaperThresholdInterval OBJECT-TYPE
    SYNTAX     CmPmIntervalType
    MAX-ACCESS read-only
    STATUS     current
    DESCRIPTION
        "The interval over which monitored value is
        sampled and compared with the specified threshold."
    ::= { f3NetPortFpQosShaperThresholdEntry 2 }

f3NetPortFpQosShaperThresholdVariable OBJECT-TYPE
    SYNTAX     VariablePointer
    MAX-ACCESS read-only
    STATUS     current
    DESCRIPTION
        "The object identifier of the particular variable to be
        sampled."
    ::= { f3NetPortFpQosShaperThresholdEntry 3 }

f3NetPortFpQosShaperThresholdValueLo OBJECT-TYPE
    SYNTAX     Unsigned32
    MAX-ACCESS read-write
    STATUS     current
    DESCRIPTION
        "Lower 32 bits of the threshold value."
    ::= { f3NetPortFpQosShaperThresholdEntry 4 }

f3NetPortFpQosShaperThresholdValueHi OBJECT-TYPE
    SYNTAX     Unsigned32
    MAX-ACCESS read-write
    STATUS     current
    DESCRIPTION
        "Higher 32 bits of the threshold value."
    ::= { f3NetPortFpQosShaperThresholdEntry 5 }

f3NetPortFpQosShaperThresholdMonValue OBJECT-TYPE
    SYNTAX     Counter64
    MAX-ACCESS read-only
    STATUS     current
    DESCRIPTION
        "Monitored value corresponding to f3NetPortFpQosShaperThresholdVariable."
    ::= { f3NetPortFpQosShaperThresholdEntry 6 }

--
-- Notifications
--

f3AccFlowPointThresholdCrossingAlert NOTIFICATION-TYPE
    OBJECTS {
                f3AccFlowPointThresholdIndex,
                f3AccFlowPointThresholdInterval,
                f3AccFlowPointThresholdVariable,
                f3AccFlowPointThresholdValueLo,
                f3AccFlowPointThresholdValueHi,
                f3AccFlowPointThresholdMonValue
            }
    STATUS  current
    DESCRIPTION
            "This trap is sent each time a threshold on a PM condition
             on an Ethernet Access Port FlowPoint is crossed."
  ::= { f3FpmPerfNotifications 1 }

f3NetFlowPointThresholdCrossingAlert NOTIFICATION-TYPE
    OBJECTS {
                f3NetFlowPointThresholdIndex,
                f3NetFlowPointThresholdInterval,
                f3NetFlowPointThresholdVariable,
                f3NetFlowPointThresholdValueLo,
                f3NetFlowPointThresholdValueHi,
                f3NetFlowPointThresholdMonValue
            }
    STATUS  current
    DESCRIPTION
            "This trap is sent each time a threshold on a PM condition
             on an Ethernet Network Port FlowPoint is crossed."
  ::= { f3FpmPerfNotifications 2 }

f3MPFlowThresholdCrossingAlert NOTIFICATION-TYPE
    OBJECTS {
                f3MPFlowThresholdIndex,
                f3MPFlowThresholdInterval,
                f3MPFlowThresholdVariable,
                f3MPFlowThresholdValueLo,
                f3MPFlowThresholdValueHi,
                f3MPFlowThresholdMonValue
            }
    STATUS  current
    DESCRIPTION
            "This trap is sent each time a threshold on a PM condition
             on an MP Flow is crossed."
  ::= { f3FpmPerfNotifications 3 }

f3AccFpQosShaperThresholdCrossingAlert NOTIFICATION-TYPE
    OBJECTS {
                f3AccFpQosShaperThresholdIndex,
                f3AccFpQosShaperThresholdInterval,
                f3AccFpQosShaperThresholdVariable,
                f3AccFpQosShaperThresholdValueLo,
                f3AccFpQosShaperThresholdValueHi,
                f3AccFpQosShaperThresholdMonValue
            }
    STATUS  current
    DESCRIPTION
            "This trap is sent each time a threshold on a PM condition
             on an Acc FlowPoint QoS Shaper is crossed."
  ::= { f3FpmPerfNotifications 4 }

f3NetFpQosShaperThresholdCrossingAlert NOTIFICATION-TYPE
    OBJECTS {
                f3NetFpQosShaperThresholdIndex,
                f3NetFpQosShaperThresholdInterval,
                f3NetFpQosShaperThresholdVariable,
                f3NetFpQosShaperThresholdValueLo,
                f3NetFpQosShaperThresholdValueHi,
                f3NetFpQosShaperThresholdMonValue
            }
    STATUS  current
    DESCRIPTION
            "This trap is sent each time a threshold on a PM condition
             on an Net FlowPoint QoS Shaper is crossed."
  ::= { f3FpmPerfNotifications 5 }

f3AccFpQosPolicerThresholdCrossingAlert NOTIFICATION-TYPE
    OBJECTS {
                f3AccFpQosPolicerThresholdIndex,
                f3AccFpQosPolicerThresholdInterval,
                f3AccFpQosPolicerThresholdVariable,
                f3AccFpQosPolicerThresholdValueLo,
                f3AccFpQosPolicerThresholdValueHi,
                f3AccFpQosPolicerThresholdMonValue
            }
    STATUS  current
    DESCRIPTION
            "This trap is sent each time a threshold on a PM condition
             on an Acc FlowPoint QoS Policer is crossed."
  ::= { f3FpmPerfNotifications 6 }

f3NetFpQosPolicerThresholdCrossingAlert NOTIFICATION-TYPE
    OBJECTS {
                f3NetFpQosPolicerThresholdIndex,
                f3NetFpQosPolicerThresholdInterval,
                f3NetFpQosPolicerThresholdVariable,
                f3NetFpQosPolicerThresholdValueLo,
                f3NetFpQosPolicerThresholdValueHi,
                f3NetFpQosPolicerThresholdMonValue
            }
    STATUS  current
    DESCRIPTION
            "This trap is sent each time a threshold on a PM condition
             on an Net FlowPoint QoS Policer is crossed."
  ::= { f3FpmPerfNotifications 7 }

f3AccPortFpQosShaperThresholdCrossingAlert NOTIFICATION-TYPE
    OBJECTS {
                f3AccPortFpQosShaperThresholdIndex,
                f3AccPortFpQosShaperThresholdInterval,
                f3AccPortFpQosShaperThresholdVariable,
                f3AccPortFpQosShaperThresholdValueLo,
                f3AccPortFpQosShaperThresholdValueHi,
                f3AccPortFpQosShaperThresholdMonValue
            }
    STATUS  current
    DESCRIPTION
            "This trap is sent each time a threshold on a PM condition
             on an Acc Port QoS Shaper is crossed."
  ::= { f3FpmPerfNotifications 8 }

f3NetPortFpQosShaperThresholdCrossingAlert NOTIFICATION-TYPE
    OBJECTS {
                f3NetPortFpQosShaperThresholdIndex,
                f3NetPortFpQosShaperThresholdInterval,
                f3NetPortFpQosShaperThresholdVariable,
                f3NetPortFpQosShaperThresholdValueLo,
                f3NetPortFpQosShaperThresholdValueHi,
                f3NetPortFpQosShaperThresholdMonValue
            }
    STATUS  current
    DESCRIPTION
            "This trap is sent each time a threshold on a PM condition
             on an Net Port QoS Shaper is crossed."
  ::= { f3FpmPerfNotifications 9 }

--
-- Conformance
--

f3FpmCompliances OBJECT IDENTIFIER ::= {f3FpmConformance 1}
f3FpmGroups    OBJECT IDENTIFIER ::= {f3FpmConformance 2}

f3FpmCompliance MODULE-COMPLIANCE
    STATUS  current
    DESCRIPTION
            "Describes the requirements for conformance to the F3-FPM-MIB compilance."
    MODULE  -- this module
        MANDATORY-GROUPS {
           f3AccFlowPointGroup,
           f3AccFpQosShaperGroup,
           f3AccFpQosPolicerGroup,
           f3MPFlowExtGroup,
           f3AccFlowPointCpdV2Group,
           f3AccFlowPointLearningConfigGroup,
           f3NetFlowPointGroup,
           f3NetFpQosShaperGroup,
           f3NetFpQosPolicerGroup,
           f3NetFlowPointCpdV2Group,
           f3NetFlowPointLearningConfigGroup,
           f3AccFlowPointPerfGroup,
           f3NetFlowPointPerfGroup,
           f3MPFlowPerfGroup,
           f3AccFpQosShaperPerfGroup,
           f3NetFpQosShaperPerfGroup,
           f3AccFpQosPolicerPerfGroup,
           f3NetFpQosPolicerPerfGroup,
           f3FpmPerfNotifGroup,
           f3AccPortFpQosShaperGroup,
           f3NetPortFpQosShaperGroup,
           f3AccPortFpQosShaperPerfGroup,
           f3NetPortFpQosShaperPerfGroup
        }
    ::= { f3FpmCompliances 1 }

f3AccFlowPointGroup OBJECT-GROUP
    OBJECTS {
       f3AccFlowPointAlias,
       f3AccFlowPointAdminState,
       f3AccFlowPointOperationalState,
       f3AccFlowPointSecondaryState,
       f3AccFlowPointAssociatedFlowId,
       f3AccFlowPointIngressMultiCOSEnabled,
       f3AccFlowPointIngressCOS,
       f3AccFlowPointEgressShapingType,
       f3AccFlowPointIngressVlanMemberList,
       f3AccFlowPointVlanMemberAction,
       f3AccFlowPointVlanMemberActionVlan,
       f3AccFlowPointIngressUntaggedFrameEnabled,
       f3AccFlowPointCTagControl,
       f3AccFlowPointCTagVlanId,
       f3AccFlowPointCTagVlanPriority,
       f3AccFlowPointSTagControl,
       f3AccFlowPointSTagVlanId,
       f3AccFlowPointSTagVlanPriority,
       f3AccFlowPointEgressOuterTagPrioMapEnabled,
       f3AccFlowPointEgressInnerTagPrioMapEnabled,
       f3AccFlowPointSESFramesLossThresholdRatio,
       f3AccFlowPointDefaultMemberEnabled,
       f3AccFlowPointMcastRateLimitEnabled,
       f3AccFlowPointMcastRateLimitSpeedLo,
       f3AccFlowPointMcastRateLimitSpeedHi,
       f3AccFlowPointBcastRateLimitEnabled,
       f3AccFlowPointBcastRateLimitSpeedLo,
       f3AccFlowPointBcastRateLimitSpeedHi,
       f3AccFlowPointCombinedRateLimitEnabled,
       f3AccFlowPointCombinedRateLimitSpeedLo,
       f3AccFlowPointCombinedRateLimitSpeedHi,
       f3AccFlowPointSplitHorizonGroupOID,
       f3AccFlowPointLoopAvoidance,
       f3AccFlowPointHierarchicalCOSEnabled,
       f3AccFlowPointMaximumBWLo,
       f3AccFlowPointMaximumBWHi,
       f3AccFlowPointGuaranteedBWLo,
       f3AccFlowPointGuaranteedBWHi,
       f3AccFlowPointAutoBandwidthConfigEnabled,
       f3AccFlowPointAutoCIRPercentage,
       f3AccFlowPointFrameFwdEnabled,
       f3AccFlowPointStorageType,
       f3AccFlowPointRowStatus,
       f3AccFlowPointUsePortPrioMapProfile,
       f3AccFlowPointRefPrioMapProfile,
       f3AccFlowpointRefConnectGuardFlowObject,
       f3AccFlowpointSecureBlockingControl,
       f3AccFlowpointSecureState,
       f3AccFlowPointElmiEvcIdentifier
    }
    STATUS  current
    DESCRIPTION
             "A collection of Access Flow Point objects."
    ::= { f3FpmGroups 1 }
   
f3AccFpQosShaperGroup OBJECT-GROUP
    OBJECTS {
       f3AccFpQosShaperIndex,
       f3AccFpQosShaperAdminState,
       f3AccFpQosShaperOperationalState,
       f3AccFpQosShaperSecondaryState,
       f3AccFpQosShaperCIRLo,
       f3AccFpQosShaperCIRHi,
       f3AccFpQosShaperCBS,
       f3AccFpQosShaperEIRLo,
       f3AccFpQosShaperEIRHi,
       f3AccFpQosShaperEBS,
       f3AccFpQosShaperBufferSize,
       f3AccFpQosShaperCOS,
       f3AccFpQosShaperStorageType,
       f3AccFpQosShaperRowStatus
    }
    STATUS  current
    DESCRIPTION
             "A collection of Access Flow Point QoS Shaper objects."
    ::= { f3FpmGroups 2 }

f3AccFpQosPolicerGroup OBJECT-GROUP
    OBJECTS {
       f3AccFpQosPolicerAdminState,
       f3AccFpQosPolicerOperationalState,
       f3AccFpQosPolicerSecondaryState,
       f3AccFpQosPolicerCIRLo,
       f3AccFpQosPolicerCIRHi,
       f3AccFpQosPolicerEIRLo,
       f3AccFpQosPolicerEIRHi,
       f3AccFpQosPolicerCBS,
       f3AccFpQosPolicerEBS,
       f3AccFpQosPolicerAlgorithm,
       f3AccFpQosPolicerColorMode,
       f3AccFpQosPolicerCouplingFlag,
       f3AccFpQosPolicerStorageType,
       f3AccFpQosPolicerRowStatus
    }
    STATUS  current
    DESCRIPTION
             "A collection of Access Flow Point QoS Policer objects."
    ::= { f3FpmGroups 3 }

f3MPFlowExtGroup OBJECT-GROUP
    OBJECTS {
       f3MPFlowExtMaxFwdEntries,
       f3MPFlowRefConnectGuardFlowObject,
       f3MPFlowSecureState
    }
    STATUS  current
    DESCRIPTION
             "A collection of MP Flow objects."
    ::= { f3FpmGroups 4 }

f3AccFlowPointCpdV2Group OBJECT-GROUP
    OBJECTS {
       f3AccFlowPointCpdV2IslDispType,
       f3AccFlowPointCpdV2PagpDispType,
       f3AccFlowPointCpdV2UdldDispType,
       f3AccFlowPointCpdV2CdpDispType,
       f3AccFlowPointCpdV2VtpDispType,
       f3AccFlowPointCpdV2DtpDispType,
       f3AccFlowPointCpdV2PvstpPlusDispType,
       f3AccFlowPointCpdV2UplinkFastDispType,
       f3AccFlowPointCpdV2VlanBridgeDispType,
       f3AccFlowPointCpdV2L2PTDispType,
       f3AccFlowPointCpdV2BPDUDispType,
       f3AccFlowPointCpdV2PauseDispType,
       f3AccFlowPointCpdV2LACPDispType,
       f3AccFlowPointCpdV2LACPMarkerDispType,
       f3AccFlowPointCpdV2EfmOamDispType,
       f3AccFlowPointCpdV2SSMDispType,
       f3AccFlowPointCpdV2PortAuthenDispType,
       f3AccFlowPointCpdV2LANBridgesDispType,
       f3AccFlowPointCpdV2GMRPDispType,
       f3AccFlowPointCpdV2GVRPDispType,
       f3AccFlowPointCpdV2GARPDispType,
       f3AccFlowPointCpdV2ActiveControlProtocols,
       f3AccFlowPointCpdV2ELMIDispType,
       f3AccFlowPointCpdV2Mac00DispType,
       f3AccFlowPointCpdV2Mac01DispType,
       f3AccFlowPointCpdV2Mac02DispType,
       f3AccFlowPointCpdV2Mac03DispType,
       f3AccFlowPointCpdV2Mac04DispType,
       f3AccFlowPointCpdV2Mac05DispType,
       f3AccFlowPointCpdV2Mac06DispType,
       f3AccFlowPointCpdV2Mac07DispType,
       f3AccFlowPointCpdV2Mac08DispType,
       f3AccFlowPointCpdV2Mac09DispType,
       f3AccFlowPointCpdV2Mac0ADispType,
       f3AccFlowPointCpdV2Mac0BDispType,
       f3AccFlowPointCpdV2Mac0CDispType,
       f3AccFlowPointCpdV2Mac0DDispType,
       f3AccFlowPointCpdV2Mac0EDispType,
       f3AccFlowPointCpdV2Mac0FDispType,
       f3AccFlowPointCpdV2NearestLLDPDispType,
       f3AccFlowPointCpdV2NonTpmrLLDPDispType,
       f3AccFlowPointCpdV2CustomerLLDPDispType
    }
    STATUS  current
    DESCRIPTION
             "A collection of Access Flow Point CDPV2 objects."
    ::= { f3FpmGroups 5 }
    
f3AccFlowPointLearningConfigGroup OBJECT-GROUP
    OBJECTS {
       f3AccFlowPointLearningConfigLearningEnabled,
       f3AccFlowPointLearningConfigMaxFwdEntries,
       f3AccFlowPointLearningConfigProtectLearningCtrl,
       f3AccFlowPointLearningConfigAction
    }
    STATUS  current
    DESCRIPTION
             "A collection of Access Flowpoint Learning Config objects."
    ::= { f3FpmGroups 6 }

f3NetFlowPointGroup OBJECT-GROUP
    OBJECTS {
       f3NetFlowPointAlias,
       f3NetFlowPointAdminState,
       f3NetFlowPointOperationalState,
       f3NetFlowPointSecondaryState,
       f3NetFlowPointAssociatedFlowId,
       f3NetFlowPointIngressMultiCOSEnabled,
       f3NetFlowPointIngressCOS,
       f3NetFlowPointEgressShapingType,
       f3NetFlowPointIngressVlanMemberList,
       f3NetFlowPointVlanMemberAction,
       f3NetFlowPointVlanMemberActionVlan,
       f3NetFlowPointIngressUntaggedFrameEnabled,
       f3NetFlowPointCTagControl,
       f3NetFlowPointCTagVlanId,
       f3NetFlowPointCTagVlanPriority,
       f3NetFlowPointSTagControl,
       f3NetFlowPointSTagVlanId,
       f3NetFlowPointSTagVlanPriority,
       f3NetFlowPointEgressOuterTagPrioMapEnabled,
       f3NetFlowPointEgressInnerTagPrioMapEnabled,
       f3NetFlowPointSESFramesLossThresholdRatio,
       f3NetFlowPointDefaultMemberEnabled,
       f3NetFlowPointMcastRateLimitEnabled,
       f3NetFlowPointMcastRateLimitSpeedLo,
       f3NetFlowPointMcastRateLimitSpeedHi,
       f3NetFlowPointBcastRateLimitEnabled,
       f3NetFlowPointBcastRateLimitSpeedLo,
       f3NetFlowPointBcastRateLimitSpeedHi,
       f3NetFlowPointCombinedRateLimitEnabled,
       f3NetFlowPointCombinedRateLimitSpeedLo,
       f3NetFlowPointCombinedRateLimitSpeedHi,
       f3NetFlowPointSplitHorizonGroupOID,
       f3NetFlowPointLoopAvoidance,
       f3NetFlowPointHierarchicalCOSEnabled,
       f3NetFlowPointMaximumBWLo,
       f3NetFlowPointMaximumBWHi,
       f3NetFlowPointGuaranteedBWLo,
       f3NetFlowPointGuaranteedBWHi,
       f3NetFlowPointAutoBandwidthConfigEnabled,
       f3NetFlowPointAutoCIRPercentage,
       f3NetFlowPointFrameFwdEnabled,
       f3NetFlowPointStorageType,
       f3NetFlowPointRowStatus,
       f3NetFlowPointUsePortPrioMapProfile,
       f3NetFlowPointRefPrioMapProfile,
       f3NetFlowpointRefConnectGuardFlowObject,
       f3NetFlowpointSecureBlockingControl,
       f3NetFlowpointSecureState,
       f3NetFlowPointElmiEvcIdentifier
    }
    STATUS  current
    DESCRIPTION
             "A collection of Network Flow Point objects."
    ::= { f3FpmGroups 7 }
   
f3NetFpQosShaperGroup OBJECT-GROUP
    OBJECTS {
       f3NetFpQosShaperIndex,
       f3NetFpQosShaperAdminState,
       f3NetFpQosShaperOperationalState,
       f3NetFpQosShaperSecondaryState,
       f3NetFpQosShaperCIRLo,
       f3NetFpQosShaperCIRHi,
       f3NetFpQosShaperCBS,
       f3NetFpQosShaperEIRLo,
       f3NetFpQosShaperEIRHi,
       f3NetFpQosShaperEBS,
       f3NetFpQosShaperBufferSize,
       f3NetFpQosShaperCOS,
       f3NetFpQosShaperStorageType,
       f3NetFpQosShaperRowStatus
    }
    STATUS  current
    DESCRIPTION
             "A collection of Network Flow Point QoS Shaper objects."
    ::= { f3FpmGroups 8 }

f3NetFpQosPolicerGroup OBJECT-GROUP
    OBJECTS {
       f3NetFpQosPolicerAdminState,
       f3NetFpQosPolicerOperationalState,
       f3NetFpQosPolicerSecondaryState,
       f3NetFpQosPolicerCIRLo,
       f3NetFpQosPolicerCIRHi,
       f3NetFpQosPolicerEIRLo,
       f3NetFpQosPolicerEIRHi,
       f3NetFpQosPolicerCBS,
       f3NetFpQosPolicerEBS,
       f3NetFpQosPolicerAlgorithm,
       f3NetFpQosPolicerColorMode,
       f3NetFpQosPolicerCouplingFlag,
       f3NetFpQosPolicerStorageType,
       f3NetFpQosPolicerRowStatus
    }
    STATUS  current
    DESCRIPTION
             "A collection of Network Flow Point QoS Policer objects."
    ::= { f3FpmGroups 9 }

f3NetFlowPointCpdV2Group OBJECT-GROUP
    OBJECTS {
       f3NetFlowPointCpdV2IslDispType,
       f3NetFlowPointCpdV2PagpDispType,
       f3NetFlowPointCpdV2UdldDispType,
       f3NetFlowPointCpdV2CdpDispType,
       f3NetFlowPointCpdV2VtpDispType,
       f3NetFlowPointCpdV2DtpDispType,
       f3NetFlowPointCpdV2PvstpPlusDispType,
       f3NetFlowPointCpdV2UplinkFastDispType,
       f3NetFlowPointCpdV2VlanBridgeDispType,
       f3NetFlowPointCpdV2L2PTDispType,
       f3NetFlowPointCpdV2BPDUDispType,
       f3NetFlowPointCpdV2PauseDispType,
       f3NetFlowPointCpdV2LACPDispType,
       f3NetFlowPointCpdV2LACPMarkerDispType,
       f3NetFlowPointCpdV2EfmOamDispType,
       f3NetFlowPointCpdV2SSMDispType,
       f3NetFlowPointCpdV2PortAuthenDispType,
       f3NetFlowPointCpdV2LANBridgesDispType,
       f3NetFlowPointCpdV2GMRPDispType,
       f3NetFlowPointCpdV2GVRPDispType,
       f3NetFlowPointCpdV2GARPDispType,
       f3NetFlowPointCpdV2ActiveControlProtocols,
       f3NetFlowPointCpdV2ELMIDispType,
       f3NetFlowPointCpdV2Mac00DispType,
       f3NetFlowPointCpdV2Mac01DispType,
       f3NetFlowPointCpdV2Mac02DispType,
       f3NetFlowPointCpdV2Mac03DispType,
       f3NetFlowPointCpdV2Mac04DispType,
       f3NetFlowPointCpdV2Mac05DispType,
       f3NetFlowPointCpdV2Mac06DispType,
       f3NetFlowPointCpdV2Mac07DispType,
       f3NetFlowPointCpdV2Mac08DispType,
       f3NetFlowPointCpdV2Mac09DispType,
       f3NetFlowPointCpdV2Mac0ADispType,
       f3NetFlowPointCpdV2Mac0BDispType,
       f3NetFlowPointCpdV2Mac0CDispType,
       f3NetFlowPointCpdV2Mac0DDispType,
       f3NetFlowPointCpdV2Mac0EDispType,
       f3NetFlowPointCpdV2Mac0FDispType,
       f3NetFlowPointCpdV2NearestLLDPDispType,
       f3NetFlowPointCpdV2NonTpmrLLDPDispType,
       f3NetFlowPointCpdV2CustomerLLDPDispType
    }
    STATUS  current
    DESCRIPTION
             "A collection of Network Flow Point CDPV2 objects."
    ::= { f3FpmGroups 10 }
    
f3NetFlowPointLearningConfigGroup OBJECT-GROUP
    OBJECTS {
       f3NetFlowPointLearningConfigLearningEnabled,
       f3NetFlowPointLearningConfigMaxFwdEntries,
       f3NetFlowPointLearningConfigProtectLearningCtrl,
       f3NetFlowPointLearningConfigAction
    }
    STATUS  current
    DESCRIPTION
             "A collection of Network Flowpoint Learning Config objects."
    ::= { f3FpmGroups 11 }
    
f3AccFlowPointPerfGroup OBJECT-GROUP
    OBJECTS {
        f3AccFlowPointStatsIndex,
        f3AccFlowPointStatsIntervalType,
        f3AccFlowPointStatsValid,
        f3AccFlowPointStatsAction,
        f3AccFlowPointStatsL2CPFD,
        f3AccFlowPointStatsABRRx,
        f3AccFlowPointStatsABRRLRx,
        f3AccFlowPointStatsUAS,
        f3AccFlowPointStatsSES, 
        f3AccFlowPointStatsFMG,
        f3AccFlowPointStatsFMY,
        f3AccFlowPointStatsFMRD,
        f3AccFlowPointStatsFTD,
        f3AccFlowPointStatsBytesIn,
        f3AccFlowPointStatsBytesOut,
        f3AccFlowPointStatsIBRMax,
        f3AccFlowPointStatsIBRRlMax,
        f3AccFlowPointStatsIBRMin,
        f3AccFlowPointStatsIBRRlMin,
        f3AccFlowPointStatsIBR,
        f3AccFlowPointStatsIBRRl,
        f3AccFlowPointStatsFBCD,
        f3AccFlowPointStatsFMCD,
        f3AccFlowPointStatsFdRxFb,
        f3AccFlowPointStatsFdTxFb,
        f3AccFlowPointStatsFdicd,
        f3AccFlowPointStatsNumLearnTableFlushes,
        f3AccFlowPointHistoryIndex,
        f3AccFlowPointHistoryTime,
        f3AccFlowPointHistoryValid,
        f3AccFlowPointHistoryAction,
        f3AccFlowPointHistoryL2CPFD,
        f3AccFlowPointHistoryABRRx,
        f3AccFlowPointHistoryABRRLRx,
        f3AccFlowPointHistoryUAS,
        f3AccFlowPointHistorySES,
        f3AccFlowPointHistoryFMG,
        f3AccFlowPointHistoryFMY,
        f3AccFlowPointHistoryFMRD,
        f3AccFlowPointHistoryFTD,
        f3AccFlowPointHistoryBytesIn,
        f3AccFlowPointHistoryBytesOut,
        f3AccFlowPointHistoryIBRMax,
        f3AccFlowPointHistoryIBRRlMax,
        f3AccFlowPointHistoryIBRMin,
        f3AccFlowPointHistoryIBRRlMin,
        f3AccFlowPointHistoryIBR,
        f3AccFlowPointHistoryIBRRl,
        f3AccFlowPointHistoryFBCD,
        f3AccFlowPointHistoryFMCD,
        f3AccFlowPointHistoryFdRxFb,
        f3AccFlowPointHistoryFdTxFb,
        f3AccFlowPointHistoryFdicd,
        f3AccFlowPointHistoryNumLearnTableFlushes,
        f3AccFlowPointThresholdIndex,
        f3AccFlowPointThresholdInterval,
        f3AccFlowPointThresholdVariable,
        f3AccFlowPointThresholdValueLo,
        f3AccFlowPointThresholdValueHi,
        f3AccFlowPointThresholdMonValue
    }
    STATUS  current
    DESCRIPTION
             "A collection of Access Flowpoint Performance objects."
    ::= { f3FpmGroups 12 }

f3NetFlowPointPerfGroup OBJECT-GROUP
    OBJECTS {
        f3NetFlowPointStatsIndex,
        f3NetFlowPointStatsIntervalType,
        f3NetFlowPointStatsValid,
        f3NetFlowPointStatsAction,
        f3NetFlowPointStatsL2CPFD,
        f3NetFlowPointStatsABRRx,
        f3NetFlowPointStatsABRRLRx,
        f3NetFlowPointStatsUAS,
        f3NetFlowPointStatsSES, 
        f3NetFlowPointStatsFMG,
        f3NetFlowPointStatsFMY,
        f3NetFlowPointStatsFMRD,
        f3NetFlowPointStatsFTD,
        f3NetFlowPointStatsBytesIn,
        f3NetFlowPointStatsBytesOut,
        f3NetFlowPointStatsIBRMax,
        f3NetFlowPointStatsIBRRlMax,
        f3NetFlowPointStatsIBRMin,
        f3NetFlowPointStatsIBRRlMin,
        f3NetFlowPointStatsIBR,
        f3NetFlowPointStatsIBRRl,
        f3NetFlowPointStatsFBCD,
        f3NetFlowPointStatsFMCD,
        f3NetFlowPointStatsFdRxFb,
        f3NetFlowPointStatsFdTxFb,
        f3NetFlowPointStatsFdicd,
        f3NetFlowPointStatsNumLearnTableFlushes,
        f3NetFlowPointHistoryIndex,
        f3NetFlowPointHistoryTime,
        f3NetFlowPointHistoryValid,
        f3NetFlowPointHistoryAction,
        f3NetFlowPointHistoryL2CPFD,
        f3NetFlowPointHistoryABRRx,
        f3NetFlowPointHistoryABRRLRx,
        f3NetFlowPointHistoryUAS,
        f3NetFlowPointHistorySES,
        f3NetFlowPointHistoryFMG,
        f3NetFlowPointHistoryFMY,
        f3NetFlowPointHistoryFMRD,
        f3NetFlowPointHistoryFTD,
        f3NetFlowPointHistoryBytesIn,
        f3NetFlowPointHistoryBytesOut,
        f3NetFlowPointHistoryIBRMax,
        f3NetFlowPointHistoryIBRRlMax,
        f3NetFlowPointHistoryIBRMin,
        f3NetFlowPointHistoryIBRRlMin,
        f3NetFlowPointHistoryIBR,
        f3NetFlowPointHistoryIBRRl,
        f3NetFlowPointHistoryFBCD,
        f3NetFlowPointHistoryFMCD,
        f3NetFlowPointHistoryFdRxFb,
        f3NetFlowPointHistoryFdTxFb,
        f3NetFlowPointHistoryFdicd,
        f3NetFlowPointHistoryNumLearnTableFlushes,
        f3NetFlowPointThresholdIndex,
        f3NetFlowPointThresholdInterval,
        f3NetFlowPointThresholdVariable,
        f3NetFlowPointThresholdValueLo,
        f3NetFlowPointThresholdValueHi,
        f3NetFlowPointThresholdMonValue
    }
    STATUS  current
    DESCRIPTION
             "A collection of Network Flowpoint Performance objects."
    ::= { f3FpmGroups 13 }

f3MPFlowPerfGroup OBJECT-GROUP
    OBJECTS {
        f3MPFlowStatsIndex,
        f3MPFlowStatsIntervalType,
        f3MPFlowStatsValid,
        f3MPFlowStatsAction,
        f3MPFlowStatsFDStaticBlock,
        f3MPFlowStatsFDHairPin,
        f3MPFlowStatsMacTableDiscards,
        f3MPFlowStatsFDProtLearn,
        f3MPFlowHistoryIndex,
        f3MPFlowHistoryTime,
        f3MPFlowHistoryValid,
        f3MPFlowHistoryAction,
        f3MPFlowHistoryFDStaticBlock,
        f3MPFlowHistoryFDHairPin,
        f3MPFlowHistoryMacTableDiscards,
        f3MPFlowHistoryFDProtLearn,
        f3MPFlowThresholdIndex,
        f3MPFlowThresholdInterval,
        f3MPFlowThresholdVariable,
        f3MPFlowThresholdValueLo,
        f3MPFlowThresholdValueHi,
        f3MPFlowThresholdMonValue
    }
    STATUS  current
    DESCRIPTION
             "A collection of MP Flow Performance objects."
    ::= { f3FpmGroups 14 }

f3AccFpQosShaperPerfGroup OBJECT-GROUP
    OBJECTS {
        f3AccFpQosShaperStatsIndex,
        f3AccFpQosShaperStatsIntervalType,
        f3AccFpQosShaperStatsValid,
        f3AccFpQosShaperStatsAction,
        f3AccFpQosShaperStatsBT,
        f3AccFpQosShaperStatsBTD,
        f3AccFpQosShaperStatsFD,
        f3AccFpQosShaperStatsFTD,
        f3AccFpQosShaperStatsABRRL,
        f3AccFpQosShaperStatsBREDD,
        f3AccFpQosShaperStatsFREDD,
        f3AccFpQosShaperHistoryIndex,
        f3AccFpQosShaperHistoryTime,
        f3AccFpQosShaperHistoryValid,
        f3AccFpQosShaperHistoryAction,
        f3AccFpQosShaperHistoryBT,
        f3AccFpQosShaperHistoryBTD,
        f3AccFpQosShaperHistoryFD,
        f3AccFpQosShaperHistoryFTD,
        f3AccFpQosShaperHistoryABRRL,
        f3AccFpQosShaperHistoryBREDD,
        f3AccFpQosShaperHistoryFREDD,
        f3AccFpQosShaperThresholdIndex,
        f3AccFpQosShaperThresholdInterval,
        f3AccFpQosShaperThresholdVariable,
        f3AccFpQosShaperThresholdValueLo,
        f3AccFpQosShaperThresholdValueHi,
        f3AccFpQosShaperThresholdMonValue
    }
    STATUS  current
    DESCRIPTION
             "A collection of Acc FlowPoint QoS Shaper Performance objects."
    ::= { f3FpmGroups 15 }

f3NetFpQosShaperPerfGroup OBJECT-GROUP
    OBJECTS {
        f3NetFpQosShaperStatsIndex,
        f3NetFpQosShaperStatsIntervalType,
        f3NetFpQosShaperStatsValid,
        f3NetFpQosShaperStatsAction,
        f3NetFpQosShaperStatsBT,
        f3NetFpQosShaperStatsBTD,
        f3NetFpQosShaperStatsFD,
        f3NetFpQosShaperStatsFTD,
        f3NetFpQosShaperStatsABRRL,
        f3NetFpQosShaperStatsBREDD,
        f3NetFpQosShaperStatsFREDD,
        f3NetFpQosShaperHistoryIndex,
        f3NetFpQosShaperHistoryTime,
        f3NetFpQosShaperHistoryValid,
        f3NetFpQosShaperHistoryAction,
        f3NetFpQosShaperHistoryBT,
        f3NetFpQosShaperHistoryBTD,
        f3NetFpQosShaperHistoryFD,
        f3NetFpQosShaperHistoryFTD,
        f3NetFpQosShaperHistoryABRRL,
        f3NetFpQosShaperHistoryBREDD,
        f3NetFpQosShaperHistoryFREDD,
        f3NetFpQosShaperThresholdIndex,
        f3NetFpQosShaperThresholdInterval,
        f3NetFpQosShaperThresholdVariable,
        f3NetFpQosShaperThresholdValueLo,
        f3NetFpQosShaperThresholdValueHi,
        f3NetFpQosShaperThresholdMonValue
    }
    STATUS  current
    DESCRIPTION
             "A collection of Net FlowPoint QoS Shaper Performance objects."
    ::= { f3FpmGroups 16 }

f3AccFpQosPolicerPerfGroup OBJECT-GROUP
    OBJECTS {
        f3AccFpQosPolicerStatsIndex,
        f3AccFpQosPolicerStatsIntervalType,
        f3AccFpQosPolicerStatsValid,
        f3AccFpQosPolicerStatsAction,
        f3AccFpQosPolicerStatsFMG,
        f3AccFpQosPolicerStatsFMY,
        f3AccFpQosPolicerStatsFMRD,
        f3AccFpQosPolicerStatsBytesIn,
        f3AccFpQosPolicerStatsBytesOut,
        f3AccFpQosPolicerStatsABR,
        f3AccFpQosPolicerHistoryIndex,
        f3AccFpQosPolicerHistoryTime,
        f3AccFpQosPolicerHistoryValid,
        f3AccFpQosPolicerHistoryAction,
        f3AccFpQosPolicerHistoryFMG,
        f3AccFpQosPolicerHistoryFMY,
        f3AccFpQosPolicerHistoryFMRD,
        f3AccFpQosPolicerHistoryBytesIn,
        f3AccFpQosPolicerHistoryBytesOut,
        f3AccFpQosPolicerHistoryABR,
        f3AccFpQosPolicerThresholdIndex,
        f3AccFpQosPolicerThresholdInterval,
        f3AccFpQosPolicerThresholdVariable,
        f3AccFpQosPolicerThresholdValueLo,
        f3AccFpQosPolicerThresholdValueHi,
        f3AccFpQosPolicerThresholdMonValue
    }
    STATUS  current
    DESCRIPTION
             "A collection of Acc FlowPoint QoS Policer Performance objects."
    ::= { f3FpmGroups 17 }

f3NetFpQosPolicerPerfGroup OBJECT-GROUP
    OBJECTS {
        f3NetFpQosPolicerStatsIndex,
        f3NetFpQosPolicerStatsIntervalType,
        f3NetFpQosPolicerStatsValid,
        f3NetFpQosPolicerStatsAction,
        f3NetFpQosPolicerStatsFMG,
        f3NetFpQosPolicerStatsFMY,
        f3NetFpQosPolicerStatsFMRD,
        f3NetFpQosPolicerStatsBytesIn,
        f3NetFpQosPolicerStatsBytesOut,
        f3NetFpQosPolicerStatsABR,
        f3NetFpQosPolicerHistoryIndex,
        f3NetFpQosPolicerHistoryTime,
        f3NetFpQosPolicerHistoryValid,
        f3NetFpQosPolicerHistoryAction,
        f3NetFpQosPolicerHistoryFMG,
        f3NetFpQosPolicerHistoryFMY,
        f3NetFpQosPolicerHistoryFMRD,
        f3NetFpQosPolicerHistoryBytesIn,
        f3NetFpQosPolicerHistoryBytesOut,
        f3NetFpQosPolicerHistoryABR,
        f3NetFpQosPolicerThresholdIndex,
        f3NetFpQosPolicerThresholdInterval,
        f3NetFpQosPolicerThresholdVariable,
        f3NetFpQosPolicerThresholdValueLo,
        f3NetFpQosPolicerThresholdValueHi,
        f3NetFpQosPolicerThresholdMonValue
    }
    STATUS  current
    DESCRIPTION
             "A collection of Net FlowPoint QoS Policer Performance objects."
    ::= { f3FpmGroups 18 }

f3FpmPerfNotifGroup NOTIFICATION-GROUP
    NOTIFICATIONS {
        f3AccFlowPointThresholdCrossingAlert,
        f3NetFlowPointThresholdCrossingAlert,
        f3MPFlowThresholdCrossingAlert,
        f3AccFpQosShaperThresholdCrossingAlert,
        f3NetFpQosShaperThresholdCrossingAlert,
        f3AccFpQosPolicerThresholdCrossingAlert,
        f3NetFpQosPolicerThresholdCrossingAlert
    }
    STATUS  current
    DESCRIPTION
            "A collection of notifications related to FSP150CC
             Threshold Crossing Alerts."
    ::= { f3FpmGroups 19 }

f3AccPortFpQosShaperGroup OBJECT-GROUP
    OBJECTS {
       f3AccPortFpQosShaperIndex,
       f3AccPortFpQosShaperAdminState,
       f3AccPortFpQosShaperOperationalState,
       f3AccPortFpQosShaperSecondaryState,
       f3AccPortFpQosShaperCIRLo,
       f3AccPortFpQosShaperCIRHi,
       f3AccPortFpQosShaperCBS,
       f3AccPortFpQosShaperEIRLo,
       f3AccPortFpQosShaperEIRHi,
       f3AccPortFpQosShaperEBS,
       f3AccPortFpQosShaperBufferSize,
       f3AccPortFpQosShaperCOS,
       f3AccPortFpQosShaperStorageType,
       f3AccPortFpQosShaperRowStatus
    }
    STATUS  current
    DESCRIPTION
             "A collection of Access Port QoS Shaper objects."
    ::= { f3FpmGroups 20 }

f3NetPortFpQosShaperGroup OBJECT-GROUP
    OBJECTS {
       f3NetPortFpQosShaperIndex,
       f3NetPortFpQosShaperAdminState,
       f3NetPortFpQosShaperOperationalState,
       f3NetPortFpQosShaperSecondaryState,
       f3NetPortFpQosShaperCIRLo,
       f3NetPortFpQosShaperCIRHi,
       f3NetPortFpQosShaperCBS,
       f3NetPortFpQosShaperEIRLo,
       f3NetPortFpQosShaperEIRHi,
       f3NetPortFpQosShaperEBS,
       f3NetPortFpQosShaperBufferSize,
       f3NetPortFpQosShaperCOS,
       f3NetPortFpQosShaperStorageType,
       f3NetPortFpQosShaperRowStatus
    }
    STATUS  current
    DESCRIPTION
             "A collection of Network Port QoS Shaper objects."
    ::= { f3FpmGroups 21 }

f3AccPortFpQosShaperPerfGroup OBJECT-GROUP
    OBJECTS {
        f3AccPortFpQosShaperStatsIndex,
        f3AccPortFpQosShaperStatsIntervalType,
        f3AccPortFpQosShaperStatsValid,
        f3AccPortFpQosShaperStatsAction,
        f3AccPortFpQosShaperStatsBT,
        f3AccPortFpQosShaperStatsBTD,
        f3AccPortFpQosShaperStatsFD,
        f3AccPortFpQosShaperStatsFTD,
        f3AccPortFpQosShaperStatsABRRL,
        f3AccPortFpQosShaperStatsBREDD,
        f3AccPortFpQosShaperStatsFREDD,
        f3AccPortFpQosShaperHistoryIndex,
        f3AccPortFpQosShaperHistoryTime,
        f3AccPortFpQosShaperHistoryValid,
        f3AccPortFpQosShaperHistoryAction,
        f3AccPortFpQosShaperHistoryBT,
        f3AccPortFpQosShaperHistoryBTD,
        f3AccPortFpQosShaperHistoryFD,
        f3AccPortFpQosShaperHistoryFTD,
        f3AccPortFpQosShaperHistoryABRRL,
        f3AccPortFpQosShaperHistoryBREDD,
        f3AccPortFpQosShaperHistoryFREDD,
        f3AccPortFpQosShaperThresholdIndex,
        f3AccPortFpQosShaperThresholdInterval,
        f3AccPortFpQosShaperThresholdVariable,
        f3AccPortFpQosShaperThresholdValueLo,
        f3AccPortFpQosShaperThresholdValueHi,
        f3AccPortFpQosShaperThresholdMonValue
    }
    STATUS  current
    DESCRIPTION
             "A collection of Acc Port QoS Shaper Performance objects."
    ::= { f3FpmGroups 22 }

f3NetPortFpQosShaperPerfGroup OBJECT-GROUP
    OBJECTS {
        f3NetPortFpQosShaperStatsIndex,
        f3NetPortFpQosShaperStatsIntervalType,
        f3NetPortFpQosShaperStatsValid,
        f3NetPortFpQosShaperStatsAction,
        f3NetPortFpQosShaperStatsBT,
        f3NetPortFpQosShaperStatsBTD,
        f3NetPortFpQosShaperStatsFD,
        f3NetPortFpQosShaperStatsFTD,
        f3NetPortFpQosShaperStatsABRRL,
        f3NetPortFpQosShaperStatsBREDD,
        f3NetPortFpQosShaperStatsFREDD,
        f3NetPortFpQosShaperHistoryIndex,
        f3NetPortFpQosShaperHistoryTime,
        f3NetPortFpQosShaperHistoryValid,
        f3NetPortFpQosShaperHistoryAction,
        f3NetPortFpQosShaperHistoryBT,
        f3NetPortFpQosShaperHistoryBTD,
        f3NetPortFpQosShaperHistoryFD,
        f3NetPortFpQosShaperHistoryFTD,
        f3NetPortFpQosShaperHistoryABRRL,
        f3NetPortFpQosShaperHistoryBREDD,
        f3NetPortFpQosShaperHistoryFREDD,
        f3NetPortFpQosShaperThresholdIndex,
        f3NetPortFpQosShaperThresholdInterval,
        f3NetPortFpQosShaperThresholdVariable,
        f3NetPortFpQosShaperThresholdValueLo,
        f3NetPortFpQosShaperThresholdValueHi,
        f3NetPortFpQosShaperThresholdMonValue
    }
    STATUS  current
    DESCRIPTION
             "A collection of Net Port QoS Shaper Performance objects."
    ::= { f3FpmGroups 23 }

END
