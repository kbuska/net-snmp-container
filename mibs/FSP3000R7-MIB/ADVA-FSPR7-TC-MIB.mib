--  ***************************************************************************
--  ADVA-FSPR7-TC-MIB.txt
--
--               ADVA AG Optical Networking MIB File
--
--  Copyright 2011 ADVA AG Optical Networking.
--
--  All rights reserved.
--  ***************************************************************************


--  Definition of textual conventions.

ADVA-FSPR7-TC-MIB DEFINITIONS ::= BEGIN 

IMPORTS



    TEXTUAL-CONVENTION
                FROM SNMPv2-TC


    MODULE-IDENTITY,
    Integer32
                FROM SNMPv2-SMI


    fspR7
                FROM ADVA-MIB;

advaFspR7Tc MODULE-IDENTITY

    LAST-UPDATED "202307050000Z"

    ORGANIZATION "ADVA Optical Networking"

    CONTACT-INFO "EMEA Support
                  Phone : +49 89 89 0665 848
                  Fax   : +49 89 89 0665 22848
                  Email : support@advaoptical.com

                  North American Support
                  Phone : 886 442 ADVA (2382) (toll-free within the US, Canada and Mexico)
                  Fax   : + 1 806 741 8529 (elsewhere)
                  Email : support-usa@advaoptical.com

                  Asia Pacific Support
                  Phone : + 1 866 442 2382 (other toll-free numbers available in some countries)
                  Email : support-asia@advaoptical.com"

    DESCRIPTION   "This is a MIB definition for ADVA AG Optical Networking entity management."

    REVISION        "202307050000Z"
    DESCRIPTION     "FSP3000 F7 Release 22.2.1 MIB."

    REVISION        "202305160000Z"
    DESCRIPTION     "FSP3000 F7 Release 22.1.1 MIB."

    REVISION        "202110300000Z"
    DESCRIPTION     "FSP3000 F7 Release 21.1.1 MIB."

    REVISION        "202103300000Z"
    DESCRIPTION     "FSP3000 F7 Release 20.3.1 MIB."

    REVISION        "202012150000Z"
    DESCRIPTION     "FSP3000 F7 Release 20.2.1 MIB."

    REVISION        "202009080000Z"
    DESCRIPTION     "FSP3000 F7 Release 20.1.1 MIB."

    REVISION        "202004280000Z"
    DESCRIPTION     "FSP3000 F7 Release 19.3.1 MIB."

    REVISION        "202002280000Z"
    DESCRIPTION     "FSP3000 F7 Release 19.2.1 MIB."

    REVISION        "201912050000Z"
    DESCRIPTION     "FSP3000 F7 Release 19.1.2 MIB."

    REVISION        "201908120000Z"
    DESCRIPTION     "FSP3000 F7 Release 19.1.1 MIB."

    REVISION        "201904290000Z"
    DESCRIPTION     "FSP3000 F7 Release 18.2.2 MIB."

    REVISION        "201812140000Z"
    DESCRIPTION     "FSP3000 F7 Release 18.2.1 MIB."

    REVISION        "201808090000Z"
    DESCRIPTION     "FSP3000 F7 Release 18.1.1 MIB."

    REVISION        "201804170000Z"
    DESCRIPTION     "FSP3000 F7 Release 17.2.1 MIB."

    REVISION        "201803150000Z"
    DESCRIPTION     "FSP3000 F7 Release 17.1.2 MIB."

    REVISION        "201802260000Z"
    DESCRIPTION     "FSP3000 F7 Release 16.3.3 MIB."

    REVISION        "201712070000Z"
    DESCRIPTION     "FSP3000 F7 Release 17.1.1 MIB."

    REVISION        "201711010000Z"
    DESCRIPTION     "FSP3000 F7 Release 16.3.2 MIB."

    REVISION        "201709110000Z"
    DESCRIPTION     "FSP3000 F7 Release 16.3.1 MIB."

    REVISION        "201706060000Z"
    DESCRIPTION     "FSP3000 F7 Release 16.2.2 MIB."

    REVISION        "201703230000Z"
    DESCRIPTION     "FSP3000 F7 Release 16.2.1 MIB."

    REVISION        "201606010000Z"
    DESCRIPTION     "FSP3000 F7 Release 16.1.2 MIB."

    REVISION        "201604010000Z"
    DESCRIPTION     "FSP3000 F7 Release 16.1.1 MIB."

    REVISION        "201512100000Z"
    DESCRIPTION     "FSP3000 F7 Release 15.2.1 MIB."

    REVISION        "201510010000Z"
    DESCRIPTION     "FSP3000 F7 Release 15.1.2 MIB."

    REVISION        "201509030000Z"
    DESCRIPTION     "FSP3000 F7 Release 15.1.1 MIB."

    REVISION        "201503200000Z"
    DESCRIPTION     "FSP3000 F7 Release 13.3.1 MIB."

    REVISION        "201410150000Z"
    DESCRIPTION     "FSP3000 F7 Release 13.2.2 MIB."

    REVISION        "201409290000Z"
    DESCRIPTION     "FSP3000 F7 Release 13.2.1 MIB."

    REVISION        "201312040000Z"
    DESCRIPTION     "FSP3000 F7 Release 12.2.1 MIB."

    REVISION        "201308200000Z"
    DESCRIPTION     "FSP3000 F7 Release 12.1.1 MIB."

    REVISION        "201105220000Z"
    DESCRIPTION     "FSP3000 F7 Release 11.2 MIB."
    ::= { fspR7 8 }

ApsRevertMode ::= TEXTUAL-CONVENTION
  STATUS        current
  DESCRIPTION
        "Revertive Protection Switching"
  SYNTAX    INTEGER
        {
            undefined(0),
            nonrevertive(1), --Revertive Protection Switching disabled
            revertive(2) --Revertive Protection Switching enabled
        }

ApsRevertModeCaps ::= TEXTUAL-CONVENTION
  STATUS        current
  DESCRIPTION
        "Revertive Protection Switching"
  SYNTAX    BITS
        {
            capUndefined(0),
            capNonrevertive(1),
            capRevertive(2)
        }

ApsType ::= TEXTUAL-CONVENTION
  STATUS        current
  DESCRIPTION
        "Type of Automatic Protection Switching; triggered by standing conditions"
  SYNTAX    INTEGER
        {
            undefined(0),
            line(2), --SONET Linear APS, SDH Multiplex Section Protection
            sncN(3), --OTN subnetwork connection Non-intrusive
            sncI(4), --OTN subnetwork connection Inherent
            sncS(5), --OTN subnetwork connection Sublayer (TCM)
            eth(6), --Ethernet
            phys(7), --Switching based on physical layer only
            sncNPM(8), --OTN subnetwork connection Non-intrusive Path Monitoring
            sncNTCM(9), --OTN subnetwork connection Non-intrusive TCM
            sncISM(10), --OTN subnetwork connection Inherent Section Monitoring
            mux(11), --ADVA proprietary
            pcs(12), --Physical Conversion Sublayer
            ethSncI(13), --ETH VLAN G.8031 protection
            ethSncN(14), --ETH VLAN G.8031 protection
            ethSncS(15), --ETH VLAN G.8031 protection
            ethSncT(16), --ETH VLAN G.8031 protection
            sncNPCS(17), --if facility TYPE is OTN (OTU# / ODU#) Payload Data Service
            sncNLine(18), --if facility TYPE is OTN (OTU# / ODU#) payload SDH/SONET
            sncNPath(19), --if facility TYPE is OTN (OTU# / ODU#) payload SDH/SONET
            path(20) --SONET APS performed at Path layer
        }

ApsTypeCaps ::= TEXTUAL-CONVENTION
  STATUS        current
  DESCRIPTION
        "Type of Automatic Protection Switching; triggered by standing conditions"
  SYNTAX    BITS
        {
            capUndefined(0),
            capLine(2),
            capSncN(3),
            capSncI(4),
            capSncS(5),
            capEth(6),
            capPhys(7),
            capSncNPM(8),
            capSncNTCM(9),
            capSncISM(10),
            capMux(11),
            capPcs(12),
            capEthSncI(13),
            capEthSncN(14),
            capEthSncS(15),
            capEthSncT(16),
            capSncNPCS(17),
            capSncNLine(18),
            capSncNPath(19),
            capPath(20)
        }

ConnectionNotation ::= TEXTUAL-CONVENTION
  STATUS        current
  DESCRIPTION
        "Connection notation"
  SYNTAX    INTEGER
        {
            undefined(0),
            fromToNotation(1),
            toFromNotation(2)
        }

Counter64StringCaps ::= TEXTUAL-CONVENTION
  STATUS        current
  DESCRIPTION
        ""
  SYNTAX    OCTET STRING (SIZE(0..16))

CryptoFspR7EncryptionCommunication ::= TEXTUAL-CONVENTION
  STATUS        current
  DESCRIPTION
        "Embedded Communication Channel used to support Encryption"
  SYNTAX    INTEGER
        {
            undefined(0),
            tcm1(1),
            tcm2(2),
            tcm3(3),
            tcm4(4),
            tcm5(5),
            tcm6(6),
            gcc0(7),
            gcc1(8),
            gcc2(9),
            gcc1gcc2(10),
            res1(11), --ODU OH row 4 column 9 - 12
            res2(12), --ODU OH row 4 column 11 - 14
            tcm1tcm2(13),
            tcm2tcm3(14),
            tcm3tcm4(15),
            tcm4tcm5(16),
            tcm5tcm6(17),
            none(18)
        }

CryptoFspR7EncryptionCommunicationCaps ::= TEXTUAL-CONVENTION
  STATUS        current
  DESCRIPTION
        "Embedded Communication Channel used to support Encryption"
  SYNTAX    BITS
        {
            capUndefined(0),
            capTcm1(1),
            capTcm2(2),
            capTcm3(3),
            capTcm4(4),
            capTcm5(5),
            capTcm6(6),
            capGcc0(7),
            capGcc1(8),
            capGcc2(9),
            capGcc1gcc2(10),
            capRes1(11),
            capRes2(12),
            capTcm1tcm2(13),
            capTcm2tcm3(14),
            capTcm3tcm4(15),
            capTcm4tcm5(16),
            capTcm5tcm6(17),
            capNone(18)
        }

EntityClassName ::= TEXTUAL-CONVENTION
  STATUS        current
  DESCRIPTION
        "Entity Class Name"
  SYNTAX    INTEGER
        {
            undefined(0),
            ne(1),
            shelf(2),
            fcuc(3),
            fcu(4),
            modc(5),
            mod(6),
            psh(7),
            plc(8),
            pl(9),
            fanc(10),
            fan(11),
            ptp(12),
            fpl(13),
            ol(14),
            om(15),
            ch(16),
            pch(17),
            vch(18),
            sts1(19),
            sts3c(20),
            sts24c(21),
            sts48c(22),
            vc3(23),
            vc4(24),
            vs1(25),
            sdcc(26),
            ldcc(27),
            pdcc(28),
            eoc(29),
            gcc0(30),
            gcc1(31),
            gcc2(32),
            sc(33),
            link(34),
            otl(37),
            tifi(38),
            tifo(39),
            sh(40),
            lan(41),
            conn(42),
            ffpCh(43),
            ffpOm(44),
            crsDcn(46),
            crsCh(47),
            wch(49),
            eth(57),
            veth(58),
            fch(64),
            vc4c8(65),
            vc4c16(66),
            vs0(67),
            vsch(68),
            ech(69),
            vtp(70),
            eom(71),
            vech(72),
            vconn(73),
            otlg(74),
            owlg(75),
            rat(105),
            tc(106),
            vsffpCh(111),
            vom(116),
            vch1(118),
            ffpVch1(119),
            pc(141),
            whitelist(144),
            uch(145),
            fc(146),
            gtp(150),
            vmod(157),
            shelfmap(161),
            lldp(164),
            lm(169),
            lic(170),
            tepl(174),
            tech(175),
            otsi(178),
            appl(181),
            ffpUch(183)
        }

EntityType ::= TEXTUAL-CONVENTION
  STATUS        current
  DESCRIPTION
        "Identifies the entity type. Each NE may have their own use of
        this INTEGER value, which will defined in the conformance document
        for each individual NE MIB."
    SYNTAX    Integer32

EquipmentState ::= TEXTUAL-CONVENTION
  STATUS        current
  DESCRIPTION
        ""
    SYNTAX    INTEGER
        {
            undefined(0),
            equipped(1),
            unequipped(2)
        }

FfpType ::= TEXTUAL-CONVENTION
  STATUS        current
  DESCRIPTION
        "Keeps the information if protection is forced or normal"
  SYNTAX    INTEGER
        {
            undefined(0),
            normal(1),
            forced(2)
        }

FfpTypeCaps ::= TEXTUAL-CONVENTION
  STATUS        current
  DESCRIPTION
        "Keeps the information if protection is forced or normal"
  SYNTAX    BITS
        {
            capUndefined(0),
            capNormal(1),
            capForced(2)
        }

Grade ::= TEXTUAL-CONVENTION
  STATUS        current
  DESCRIPTION
        "Used to distinguish between NCU capabilities (range of supported services or applications)"
  SYNTAX    INTEGER
        {
            undefined(0),
            gradeA(1), --Supports: CWDM / WCA* and xTCA* (access type) modules
            gradeB(2), --Supports: same as Grade A and additionally DWDM /  WCE* and xTCE* (enterprise type) modules / WCC* and xTCC* (core type) modules / FC facilities
            gradeGdps(3), --Supports: same as Grade B and additionally GDPS
            gradeC(4)
        }

FspR7Access ::= TEXTUAL-CONVENTION
  STATUS        current
  DESCRIPTION
        "The type of access to the data"
  SYNTAX    INTEGER
        {
            undefined(0),
            readOnly(1),
            readWrite(2)
        }

FspR7AccessNcuC2 ::= TEXTUAL-CONVENTION
  STATUS        current
  DESCRIPTION
        "Controls NCU C2 port access to the Management Network (DCN)"
  SYNTAX    INTEGER
        {
            undefined(0),
            nodeOnly(1),
            network(2)
        }

FspR7AccessNcuC2Caps ::= TEXTUAL-CONVENTION
  STATUS        current
  DESCRIPTION
        "Controls NCU C2 port access to the Management Network (DCN)"
  SYNTAX    BITS
        {
            capUndefined(0),
            capNodeOnly(1),
            capNetwork(2)
        }

FspR7AccessProtocol ::= TEXTUAL-CONVENTION
  STATUS        current
  DESCRIPTION
        "Possible services accross F7 system"
  SYNTAX    INTEGER
        {
            undefined(0),
            none(1),
            serialCraft(2),
            telnetCraft(3),
            telnetTl1(4),
            sshTl1(5),
            sshCraft(6),
            sshNetconf(7),
            http(8),
            httpsNed(9),
            httpsRestconf(10),
            httpsCprest(11),
            httpNi(12),
            ftp(13),
            snmp(14),
            other(15)
        }

FspR7AccessProtocolCaps ::= TEXTUAL-CONVENTION
  STATUS        current
  DESCRIPTION
        "Possible services accross F7 system"
  SYNTAX    BITS
        {
            capUndefined(0),
            capNone(1),
            capSerialCraft(2),
            capTelnetCraft(3),
            capTelnetTl1(4),
            capSshTl1(5),
            capSshCraft(6),
            capSshNetconf(7),
            capHttp(8),
            capHttpsNed(9),
            capHttpsRestconf(10),
            capHttpsCprest(11),
            capHttpNi(12),
            capFtp(13),
            capSnmp(14),
            capOther(15)
        }

FspR7AccessStatus ::= TEXTUAL-CONVENTION
  STATUS        current
  DESCRIPTION
        "Indication whether security operation was succesful/unsuccessful."
  SYNTAX    INTEGER
        {
            undefined(0),
            none(1),
            success(2),
            authenticationError(3),
            sessionError(4),
            fail(5),
            tokenMismatch(6),
            timeRestriction(7),
            accountLocked(8)
        }

FspR7AccountFlag ::= TEXTUAL-CONVENTION
  STATUS        current
  DESCRIPTION
        ""
  SYNTAX    INTEGER
        {
            undefined(0),
            none(1),
            authForced(2)
        }

FspR7AccState ::= TEXTUAL-CONVENTION
  STATUS        current
  DESCRIPTION
        ""
  SYNTAX    INTEGER
        {
            undefined(0),
            unlocked(1),
            locked(2),
            inactivityLock(3),
            failLoginlock(4),
            expired(5)
        }

FspR7AccStateTrap ::= TEXTUAL-CONVENTION
  STATUS        current
  DESCRIPTION
        "User account state."
  SYNTAX    INTEGER
        {
            undefined(0),
            invalid(1),
            unlocked(2),
            manualLock(3),
            inactivityLock(4),
            failLoginlock(5),
            expired(6)
        }

FspR7Acp ::= TEXTUAL-CONVENTION
  STATUS        current
  DESCRIPTION
        "APS communication partner"
  SYNTAX    INTEGER
        {
            undefined(0),
            none(1), --No APS channel partner
            epte1(2), --PEER-AID1 is APS channel partner
            epte2(3), --PEER-AID2 is APS channel partner
            epte3(4), --PEER-AID2 is APS channel partner
            epte4(5) --PEER-AID4 is APS channel partner
        }

FspR7AcpCaps ::= TEXTUAL-CONVENTION
  STATUS        current
  DESCRIPTION
        "APS communication partner"
  SYNTAX    BITS
        {
            capUndefined(0),
            capNone(1),
            capEpte1(2),
            capEpte2(3),
            capEpte3(4),
            capEpte4(5)
        }

FspR7ActivePassive ::= TEXTUAL-CONVENTION
  STATUS        current
  DESCRIPTION
        "Enable/Disable variable."
  SYNTAX    INTEGER
        {
            undefined(0),
            active(1),
            passive(2)
        }

FspR7AdminState ::= TEXTUAL-CONVENTION
  STATUS        current
  DESCRIPTION
        "Administrative State is displayed in the GUI and Craft. Transition to Unassigend requires the entity to be deleted."
  SYNTAX    INTEGER
        {
            undefined(0),
            uas(1),
            is(2),
            ains(3),
            mgt(4),
            mt(5),
            dsbld(6),
            pps(7)
        }

FspR7AdminStateCaps ::= TEXTUAL-CONVENTION
  STATUS        current
  DESCRIPTION
        "Administrative State is displayed in the GUI and Craft. Transition to Unassigend requires the entity to be deleted."
  SYNTAX    BITS
        {
            capUndefined(0),
            capUas(1),
            capIs(2),
            capAins(3),
            capMgt(4),
            capMt(5),
            capDsbld(6),
            capPps(7)
        }

FspR7AidType ::= TEXTUAL-CONVENTION
  STATUS        current
  DESCRIPTION
        "Type of Access Identifier"
  SYNTAX    INTEGER
        {
            undefined(0),
            none(1),
            sys(2),
            eqpt(3),
            ch(4),
            dcn(5),
            ol(6),
            om(7),
            sts1(8),
            sts3c(9),
            sts24c(10),
            sts48c(11),
            vc3(12),
            vc4(13),
            vs1(14),
            vs4c(15),
            sh(16),
            lif(17),
            lifCp(18),
            tnlWdm(19),
            vc4c8(20),
            vc4c16(21),
            otl(22),
            tnlEth(24),
            tnlOtn(25),
            speq(23),
            lldp(26),
            shelfmap(27),
            lm(28),
            lic(29),
            otsi(30),
            key(31),
            cert(32),
            ca(33),
            appl(34)
        }

FspR7AlarmListType ::= TEXTUAL-CONVENTION
  STATUS        current
  DESCRIPTION
        "List of standing condition alarms supported by ADVA-FSPR7-MIB"
  SYNTAX        INTEGER
                {
                  undefined(0),
               terminalLoopback(5),
               oosDisabled(6),
               oosManagement(7),
               oosMaintenance(8),
               oosAins(9),
               removed(10),
               lossOfSignal(11),
               optInputPwrReceivedTooLow(12),
               optInputPwrReceivedTooHigh(13),
               laserTemperatureTooHigh(14),
               laserTemperatureTooLow(15),
               optOutputPowerTransTooLow(16),
               optOutputPowerTransTooHigh(17),
               autoShutdownToHighTemp(18),
               autoShutdownToHighTxPwr(19),
               laserEndOfLife(20),
               serverSignalFailureVf(21),
               equalizationProgress(22),
               uPortFailure(23),
               autoShutdownBlock(24),
               autoPowerShutdown(25),
               confOutPowerTransTooHigh(26),
               confOutPowerTransTooLow(27),
               optSignalFailure(28),
               dsbdChannelPowerTooHigh(29),
               lossOfSignalCPort(30),
               lossOfSignalNPort(31),
               outputPowerFault(32),
               eqlzAdjust(33),
               ampFailure(34),
               eqptProvMismatch(35),
               backreflectionTooHigh(36),
               fiberConnLos(48),
               fiberConnOptFault(49),
               fiberConnInvalid(50),
               fiberConnMismatch(51),
               fiberConnCommError(52),
               fiberConnProtocolFailure(53),
               fiberConnDataFailure(54),
               fiberAttenuationHigh(55),
               laserBiasCurrAbnormal(57),
               fiberConnInvalidTx(58),
               fiberConnMismatchTx(59),
               fiberAttenuationHighTx(60),
               laserFailure(61),
               lossOfReceiverClockRecovery(62),
               fiberAttenuationCond(63),
               channelMismatch(64),
               alarmIndicationSignalLine(65),
               alarmIndicationSignalLowerOrderPath(66),
               alarmIndicationSignalOdu(67),
               alarmIndicationSignalOpu(68),
               alarmIndicationSignalOtu(69),
               alarmIndicationSignalHigherOrderPath(70),
               alarmIndicationSignalOduTcmA(71),
               alarmIndicationSignalOduTcmB(72),
               alarmIndicationSignalOduTcmC(73),
               virtualChannelAis(74),
               amplifierAbnormal(75),
               automaticPowerReduction(76),
               automaticPowerReductionForEyeSafety(77),
               apsConfigMismatch(80),
               apsProtocolFailure(81),
               aseLow(82),
               aseTableGenFailLow(83),
               aseTableGenFailHighBackreflection(84),
               aseTableGenFailOscMissing(85),
               aseTableGenFailPilot(86),
               aseTableGenFailSignalinput(87),
               aseTableNotAvailable(88),
               aseTableGenProgress(89),
               encryptionPortAuthPasswdMissing(90),
               backwardDefectIndicationOdu(92),
               backwardDefectIndicationOtu(93),
               backwardDefectIndicationOduTcmA(94),
               backwardDefectIndicationOduTcmB(95),
               backwardDefectIndicationOduTcmC(96),
               topologyDataCalculationInProgress(97),
               dispertionTunningCondition(99),
               lossOfCharSync(100),
               lossOfCharSyncFromFarEnd(101),
               encryptionPortEncryptionSwitchOffEnabled(103),
               encryptionModuleCryPasswdMissing(104),
               encryptionModuleSelfTestStarted(107),
               encryptionPortEncryptionSwitchedOff(108),
               opuClientSignalFail(109),
               databaseMismatch(110),
               databaseFailure(111),
               databaseNcuMismatch(112),
               dbReplicationIncompleted(113),
               databaseVersionMismatch(114),
               xfpDecisionThresSetFailed(115),
               duplexLinkFailure(116),
               singleFanFailure(118),
               multipleFanFailure(119),
               lossOfSignalTransmitter(120),
               farEndIpAddressUnknown(122),
               farEndCommFailure(123),
               backupForcedToHalt(125),
               facilityForcedOn(127),
               fwdAseTableFailPilot(128),
               fwdAseTableOnPilot(129),
               encryptionModuleFwpUpdateEnabled(131),
               fwpMismatchDownloadNotServiceAffecting(132),
               fwpMismatchDownloadServiceAffecting(133),
               gainTiltNotSettable(135),
               highBer(136),
               receiverOverloadProtection(137),
               hwInitializing(138),
               hwOprReachedHT(139),
               hwDegrade(140),
               hwFailure(141),
               switchtoProtectionInhibited(142),
               switchtoWorkingInhibited(143),
               encryptionPortKeyInitExchgMissed(148),
               encryptionPortMaxKeyExchgFailuresReachedIs(149),
               encryptionPortMaxKeyExchgFailuresReachedOos(150),
               encryptionPortKeyExchangedForced(151),
               laserOnDelay(152),
               lockedDefectOdu(153),
               lockedDefectOduTcmA(154),
               lockedDefectOduTcmB(155),
               lockedDefectOduTcmC(156),
               linkControlProtocolFailure(157),
               linkDown(158),
               autoShutdownSendingAisLine(159),
               autoShutdownSendingAisOdu(160),
               autoShutdownSendingAisOpu(161),
               clientFailForwarding(162),
               autoShutdownAls(163),
               autoAmpShutdown(164),
               autoShutdownAmpAps(165),
               aseTableBuild(166),
               autoShutdownOpuClientSignalFail(167),
               autoShutdownSendingEPC(168),
               autoShutdownSendingLckOdu(169),
               autoShutdownSendingOciOdu(170),
               autoShutdownLaserOffDueToErrFwd(171),
               autoShutdownTxRxLasersDueToHighTemp(172),
               localFault(173),
               localOscLevelAbnormal(174),
               lossOfGfpFrame(175),
               lossOfFrameMux(176),
               lossOfFrameOtu(177),
               lossOfFrame(178),
               lossOfFrameLossOfMultiFrameOdu(179),
               lossOfLane(180),
               lossofMultiframeLowerOrderPath(181),
               lossOfMultiFrameOtu(182),
               lossofMultiframeHigherOrderPath(183),
               lossOfPointerLowerOrderPath(184),
               lossOfPointerHigherOrderPath(185),
               losAttProgress(186),
               lossOsc(187),
               gfpLossOfClientSig(188),
               loopbackError(189),
               facilityLoopback(190),
               lossofTandemConnectionOduTcmA(191),
               lossofTandemConnectionOduTcmB(192),
               lossofTandemConnectionOduTcmC(193),
               mansw(194),
               equipmentNotAccepted(197),
               equipmentNotApproved(198),
               capabilityLevelMismatch(199),
               equipmentMismatch(200),
               equipmentNotSupportedByPhysicalLayer(201),
               meaSwRevision(202),
               mismatch(203),
               midstageFault(204),
               multiplexStructureIdentifierMismatchOPU(205),
               backupNotResponding(206),
               openConnectionIndicationOdu(207),
               openConnectionIndicationOduTcmA(208),
               openConnectionIndicationOduTcmB(209),
               openConnectionIndicationOduTcmC(210),
               oduTribMsiMismatch(211),
               transmitterDisabledOff(212),
               receiverDisabled(213),
               opmAbnormalCondition(214),
               faultOnOpm(215),
               thresOptPowerCtrlFailureHigh(216),
               thresOptPowerCtrlFailureLow(217),
               txPowerLimited(218),
               oscOpticalPowerControlFailHigh(219),
               oscOpticalPowerControlFailLow(220),
               oTDRMeasuringinProgress(221),
               encryptionModuleCryPasswdError(222),
               peerLink(223),
               pilotReceiveLevelHigh(224),
               lossOfPilotSignal(225),
               payloadMismatchGfp(226),
               payloadMismatchLowerOrderPath(227),
               payloadMismatchOPU(228),
               payloadMismatchHigherOrderPath(229),
               provPayloadMismatch(230),
               prbsLossOfSeqSynch(231),
               prbsRcvActivated(232),
               prbsTrmtActivated(233),
               protectionNotAvailable(234),
               powerSupplyUnitFailure(235),
               maxPowerConsProvModulesToHigh(236),
               maxPowerConsEquipModulesToHigh(237),
               powerMissing(238),
               remoteDefectIndicationLine(239),
               remoteDefectIndicationLowerOrderPath(240),
               remoteDefectIndicationHigherOrderPath(241),
               dcnCommunicationFail(243),
               ntpForSchedEqlzRequired(244),
               signalDegradeOlm(245),
               signalDegradeLine(246),
               signalDegradationonLinkVector(247),
               signalDegradeOdu(248),
               signalDegradeOtu(249),
               pcsSignalDegrade(250),
               signalDegradeScn(251),
               signalDegradeOduTcmA(252),
               signalDegradeOduTcmB(253),
               signalDegradeOduTcmC(254),
               moduleSelfTestFail(255),
               moduleSelfTestFailCritical(256),
               signalFailureOnLink(257),
               signalFailureonLinkVector(258),
               signalFailureOPU(259),
               clientOutage(260),
               facilityDataRateNotSupported(261),
               lossofSequenceLowerOrderPath(263),
               lossofSequenceHigherOrderPath(264),
               serverSignalFail(265),
               serverSignalFailureGfp(266),
               serverSignalFailureODU(267),
               serverSignalFailurePath(268),
               serverSignalFailureSectionRS(269),
               switchToDuplexInhibited(272),
               switchFailed(274),
               currentTooHigh(276),
               attOnReceiverFiberHigherThanMonitor(277),
               attOnReceiverFiberLowerThanMonitor(278),
               attOnTransmitterFiberHigherThanMonitor(279),
               attOnTransmitterFiberLowerThanMonitor(280),
               thres15MinExceededOduBbe(281),
               thres15MinExceededOtuBbe(283),
               thres15MinExceededOduTcmABbe(285),
               thres15MinExceededOduTcmBBbe(287),
               thres15MinExceededOduTcmCBbe(289),
               thres15MinExceededFecBERCE(291),
               brPwrRxTooHigh(293),
               chromaticDispersionTooHigh(294),
               chromaticDispersionTooLow(295),
               dispersionCompensationTooHigh(296),
               dispersionCompensationTooLow(297),
               thres15MinExceededFecCE(298),
               carrierFreqOffsetTooHigh(300),
               carrierFreqOffsetTooLow(301),
               thres15MinExceededSonetLineCV(302),
               thres15MinExceededPhysConvCV(304),
               thres15MinExceededSonetSectCV(306),
               thres15MinExceededPhysConvDE(308),
               differentialGroupDelayTooHigh(310),
               thres15MinExceededFecES(311),
               thres15MinExceededSonetLineES(313),
               thres15MinExceededOduES(315),
               thres15MinExceededOtuES(317),
               thres15MinExceededPhysConvES(319),
               thres15MinExceededSonetSectES(321),
               thres15MinExceededOduTcmAES(323),
               thres15MinExceededOduTcmBES(325),
               thres15MinExceededOduTcmCES(327),
               latencyTooHigh(329),
               latencyTooLow(330),
               laserBiasCurrentNormalizedtooHigh(331),
               localOscTemperatureTooHigh(332),
               localOscTemperatureTooLow(333),
               pumpLaser1TempTooHigh(334),
               pumpLaser1TempTooLow(335),
               pumpLaser2TempTooHigh(336),
               pumpLaser2TempTooLow(337),
               pumpLaser3TempTooHigh(338),
               pumpLaser3TempTooLow(339),
               pumpLaser4TempTooHigh(340),
               pumpLaser4TempTooLow(341),
               oscPwrTooHigh(342),
               oscPwrTooLow(343),
               ramanPumpPwrTooHigh(344),
               ramanPumpPwrTooLow(345),
               roundTripDelayTooHigh(346),
               roundTripDelayTooLow(347),
               thres15MinExceededSonetSectSEFS(348),
               thres15MinExceededFecSES(350),
               thres15MinExceededSonetLineSES(352),
               thres15MinExceededOduSES(354),
               thres15MinExceededOtuSES(356),
               thres15MinExceededSonetSectSES(358),
               thres15MinExceededOduTcmASES(360),
               thres15MinExceededOduTcmBSES(362),
               thres15MinExceededOduTcmCSES(364),
               logicalLanesSkewTooHigh(366),
               signalToNoiseRatioTooLow(367),
               subModuleTempTooHigh(368),
               temperatureTooHigh(369),
               temperatureTooLow(370),
               thres15MinExceededSonetLineUAS(371),
               thres15MinExceededOduUAS(373),
               thres15MinExceededOtuUAS(375),
               thres15MinExceededOduTcmAUAS(377),
               thres15MinExceededOduTcmBUAS(379),
               thres15MinExceededOduTcmCUAS(381),
               thres15MinExceededFecUBE(383),
               encryptionModuleTamperDetected(385),
               thermoElectricCoolerEndOfLife(386),
               inputTIF(387),
               traceIdentifierMismatchOdu(389),
               traceIdentifierMismatchOtu(390),
               sectionTraceMismatch(391),
               traceIdentifierMismatchOduTcmA(392),
               traceIdentifierMismatchOduTcmB(393),
               traceIdentifierMismatchOduTcmC(394),
               turnupFailed(395),
               turnupCondition(396),
               unequippedLowerOrderPath(397),
               unequippedHigherOrderPath(398),
               voaControlFail(399),
               voltageOutOfRange(400),
               inputVoltageFailure(401),
               inputVoltageFailurePort1(402),
               inputVoltageFailurePort2(403),
               wtrTimerRunning(406),
               lossOfLaneOtu(407),
               lossOfTestSeqSynchOpu(408),
               lossOfMfiOpu(409),
               oosDisabledLckOduTrmt(410),
               configurationMismatch(411),
               oduAutoShutdownRxAIS(412),
               oduAutoShutdownTxAIS(413),
               oosDisabledLckOduRx(414),
               thres15MinExceededBbePcs(420),
               autoShutdownGAis(422),
               equipmentMismatchAllow(423),
               warmUp(424),
               networkPathRestricted(432),
               vfClientSignalFail(434),
               autoShutdownVfCSF(435),
               linkFailToPartner1(439),
               linkFailToPartner2(440),
               linkFailToPartner3(441),
               linkFailToPartner4(442),
               partnerUnavailable(443),
               partner1Deleted(445),
               partner2Deleted(446),
               partner3Deleted(447),
               partner4Deleted(448),
               thres15MinExceededPhysConvSE(450),
               thres15MinExceededPhysConvCVDE(452),
               autoShutdownSendingOciOduTx(456),
               acpLinkLoss(457),
               acpChannelUnAvail(458),
               acpPartnerUnassigned(459),
               acpPartnerDeleted(460),
               thres15MinExceededCrcErrorsRcv(461),
               thres15MinExceededCrcFramesEgress(463),
               autoServiceMismatch(465),
               batteryNoCharge(466),
               tagReceiveFail(469),
               tagReceiveFailMaxReached(470),
               internalEncryptionFail(473),
               insufficientPower(476),
               powerConsumptionHigh(477),
               lossOfOverhead(478),
               lossOfInputSignal(479),
               otuServerSignalFail(480),
               lossOfAlignment(482),
               localFaultRx(483),
               localFaultTx(484),
               serverSignalFailRx(485),
               serverSignalFailTx(486),
               lossOfBlockLock(487),
               inputVoltageLow(488),
               outputVoltageFailure(489),
               outputPowerHigh(490),
               communicationLoss(491),
               incompatibleVersion(492),
               airDustFilterClogged(493),
               psmRedundancyMismatch(494),
               lossOfModemSync(495),
               serverSignalFailPayload(496),
               outputCurrentDrawHigh(497),
               rAndCPortOutage(498),
               rPortOutage(499),
               pPortOutage(500),
               hwOptReachedHT(501),
               excessLLDPNeighborsRx(502),
               excessLLDPNeighborsTx(503),
               configurationFault(504),
               channelMismatchRx(505),
               lossOfCoupling(506),
               hardwareUnavailable(507),
               cryAuthKeyMissing(511),
               cryDataInvalid(512),
               lossOfSignalDcPort(513),
               ampDisabled(514),
               licenseMissing(516),
               hwConfigFault(517),
               thres15MinExceededSonetSectBbe(518),
               thres15MinExceededSonetLineBbe(520),
               serverSignalFailLine(522),
               thres15MinExceededSonetSectOofs(523),
               noLicenseFile(525),
               licenseServerDisconnected(526),
               licenseServerNotConfigured(527),
               licenseInvalid(528),
               licenseOverdraft(529),
               licenseMissingMismatch(530),
               qualityFactorTooLow(531),
               replaceAirFilter(537),
               autoShutdownSendingIdle(538),
               mpFileMissing(541),
               delayMeasurementProgress(546),
               oprSignalDegrade(549),
               licenseBkServerDisconnected(550),
               rebootInProgress(551),
               qkdConnectionFail(554),
               qkdBackplaneFail(555),
               qkdInternalFail(556),
               qkdKeyLowRate(557),
               qkdNoKey(558),
               qkdConfError(559),
               opticalSignalToNoiseTooLow(561),
               stateOfPolarizationTooHigh(562),
               cdCompensationFail(563),
               pumpCurrentHigh(564),
               pumpCurrentAbnormal(565),
               pumpCurrentLow(566),
               opticalInputPowerHigh(567),
               scepError(568),
               caAuthPending(571),
               caAuthFailed(572),
               caTrustFailed(573),
               keyGenInProgress(576),
               keyGenFailed(577),
               keyRenewalInProgress(580),
               keyRenewalFailed(581),
               certReqInProgress(584),
               certReqFailed(585),
               certIssuerError(586),
               certDateInvalid(587),
               certRevoked(588),
               certSignatureInvalid(589),
               certAttributeInvalid(590),
               certConstraintsFail(591),
               certInvalid(592),
               crlFail(593),
               crlUpdatePending(594),
               crlUpdateFail(595),
               certActivationFailed(598),
               notOperationalSequence(599),
               encryptionCommMismatch(600),
               licenseExpiresIn28Days(606),
               licenseExpiresIn7Days(607),
               commDegraded(608),
               licenseServerTimeOutOfSync(612),
               modAuthPkiInternalFail(614),
               modAuthPkiCertUpdateFail(615),
               modAuthPkiConfigMismatch(616),
               modAuthPkiPairingFail(617),
               modAuthPkiPortsNotPaired(618),
               modAuthPkiCertRetrievalFail(619),
               spanEqualizationFault(620),
               componentTemperatureHigh(621),
               protectionCommandApplied(622),
               serverSignalFailureTcmA(623),
               serverSignalFailureTcmB(624),
               serverSignalFailureTcmC(625),
               passwordMismatch(626),
               passwordChangeFail(627),
               hwBusy(628),
               licenseConnInvalid(629),
               prbsLossOfSeqSynchLane1(631),
               prbsLossOfSeqSynchLane2(632),
               prbsLossOfSeqSynchLane3(633),
               prbsLossOfSeqSynchLane4(634),
               insecureProtocolActive(641),
               certActInProgress(642),
               sequentialFwpUpdateFail(643),
               laserBiasCurrUnstable(644),
               entropyUpdateFail(645),
               linkFailToOSCPartner(646),
               inhibitAuto(647),
               flexoGroupIdentMismatch(648),
               flexoMapMismatch(649),
               flexoRemoteDefectInd(650),
               otuLossOfFrameMultiFrame(651),
               flexoServerSignalFailure(652),
               tailEndCommFail(653),
               keyPairActFail(654),
               componentTemperatureWarn(655),
               componentTemperatureSd(656),
               cryptoServiceMissing(657),
               opticalBandwidthMismatch(658),
               allLanesSummaryOutage(659),
               eepromReadFail(660),
               psmProtectFault(661),
               notEnoughPsmPower(662),
               plugCommunicationFail(663),
               appletNotInstalled(670),
               appletNotConfigured(671),
               appletPinInvalid(672),
               certExpirationWarning(677),
               ntpAuthenticationFail(678),
               webClientAuthFail(681),
               certFailRequirement(682)
                }

FspR7AlarmProfileList ::= TEXTUAL-CONVENTION
  STATUS        current
  DESCRIPTION
        ""
  SYNTAX    INTEGER
        {
            undefined(0),
            terminalLoopback(5),
            oosDisabled(6),
            oosManagement(7),
            oosMaintenance(8),
            oosAins(9),
            removed(10),
            lossOfSignal(11),
            optInputPwrReceivedTooLow(12),
            optInputPwrReceivedTooHigh(13),
            laserTemperatureTooHigh(14),
            laserTemperatureTooLow(15),
            optOutputPowerTransTooLow(16),
            optOutputPowerTransTooHigh(17),
            autoShutdownToHighTemp(18),
            autoShutdownToHighTxPwr(19),
            laserEndOfLife(20),
            serverSignalFailureVf(21),
            equalizationProgress(22),
            uPortFailure(23),
            autoShutdownBlock(24),
            autoPowerShutdown(25),
            confOutPowerTransTooHigh(26),
            confOutPowerTransTooLow(27),
            optSignalFailure(28),
            dsbdChannelPowerTooHigh(29),
            lossOfSignalCPort(30),
            lossOfSignalNPort(31),
            outputPowerFault(32),
            eqlzAdjust(33),
            ampFailure(34),
            eqptProvMismatch(35),
            backreflectionTooHigh(36),
            fiberConnLos(48),
            fiberConnOptFault(49),
            fiberConnInvalid(50),
            fiberConnMismatch(51),
            fiberConnCommError(52),
            fiberConnProtocolFailure(53),
            fiberConnDataFailure(54),
            fiberAttenuationHigh(55),
            laserBiasCurrAbnormal(57),
            fiberConnInvalidTx(58),
            fiberConnMismatchTx(59),
            fiberAttenuationHighTx(60),
            laserFailure(61),
            lossOfReceiverClockRecovery(62),
            fiberAttenuationCond(63),
            channelMismatch(64),
            alarmIndicationSignalLine(65),
            alarmIndicationSignalLowerOrderPath(66),
            alarmIndicationSignalOdu(67),
            alarmIndicationSignalOpu(68),
            alarmIndicationSignalOtu(69),
            alarmIndicationSignalHigherOrderPath(70),
            alarmIndicationSignalOduTcmA(71),
            alarmIndicationSignalOduTcmB(72),
            alarmIndicationSignalOduTcmC(73),
            virtualChannelAis(74),
            amplifierAbnormal(75),
            automaticPowerReduction(76),
            automaticPowerReductionForEyeSafety(77),
            apsConfigMismatch(80),
            apsProtocolFailure(81),
            aseLow(82),
            aseTableGenFailLow(83),
            aseTableGenFailHighBackreflection(84),
            aseTableGenFailOscMissing(85),
            aseTableGenFailPilot(86),
            aseTableGenFailSignalinput(87),
            aseTableNotAvailable(88),
            aseTableGenProgress(89),
            encryptionPortAuthPasswdMissing(90),
            backwardDefectIndicationOdu(92),
            backwardDefectIndicationOtu(93),
            backwardDefectIndicationOduTcmA(94),
            backwardDefectIndicationOduTcmB(95),
            backwardDefectIndicationOduTcmC(96),
            topologyDataCalculationInProgress(97),
            dispertionTunningCondition(99),
            lossOfCharSync(100),
            lossOfCharSyncFromFarEnd(101),
            encryptionPortEncryptionSwitchOffEnabled(103),
            encryptionModuleCryPasswdMissing(104),
            encryptionModuleSelfTestStarted(107),
            encryptionPortEncryptionSwitchedOff(108),
            opuClientSignalFail(109),
            databaseMismatch(110),
            databaseFailure(111),
            databaseNcuMismatch(112),
            dbReplicationIncompleted(113),
            databaseVersionMismatch(114),
            xfpDecisionThresSetFailed(115),
            duplexLinkFailure(116),
            singleFanFailure(118),
            multipleFanFailure(119),
            lossOfSignalTransmitter(120),
            farEndIpAddressUnknown(122),
            farEndCommFailure(123),
            backupForcedToHalt(125),
            facilityForcedOn(127),
            fwdAseTableFailPilot(128),
            fwdAseTableOnPilot(129),
            encryptionModuleFwpUpdateEnabled(131),
            fwpMismatchDownloadNotServiceAffecting(132),
            fwpMismatchDownloadServiceAffecting(133),
            gainTiltNotSettable(135),
            highBer(136),
            receiverOverloadProtection(137),
            hwInitializing(138),
            hwOprReachedHT(139),
            hwDegrade(140),
            hwFailure(141),
            switchtoProtectionInhibited(142),
            switchtoWorkingInhibited(143),
            encryptionPortKeyInitExchgMissed(148),
            encryptionPortMaxKeyExchgFailuresReachedIs(149),
            encryptionPortMaxKeyExchgFailuresReachedOos(150),
            encryptionPortKeyExchangedForced(151),
            laserOnDelay(152),
            lockedDefectOdu(153),
            lockedDefectOduTcmA(154),
            lockedDefectOduTcmB(155),
            lockedDefectOduTcmC(156),
            linkControlProtocolFailure(157),
            linkDown(158),
            autoShutdownSendingAisLine(159),
            autoShutdownSendingAisOdu(160),
            autoShutdownSendingAisOpu(161),
            clientFailForwarding(162),
            autoShutdownAls(163),
            autoAmpShutdown(164),
            autoShutdownAmpAps(165),
            aseTableBuild(166),
            autoShutdownOpuClientSignalFail(167),
            autoShutdownSendingEPC(168),
            autoShutdownSendingLckOdu(169),
            autoShutdownSendingOciOdu(170),
            autoShutdownLaserOffDueToErrFwd(171),
            autoShutdownTxRxLasersDueToHighTemp(172),
            localFault(173),
            localOscLevelAbnormal(174),
            lossOfGfpFrame(175),
            lossOfFrameMux(176),
            lossOfFrameOtu(177),
            lossOfFrame(178),
            lossOfFrameLossOfMultiFrameOdu(179),
            lossOfLane(180),
            lossofMultiframeLowerOrderPath(181),
            lossOfMultiFrameOtu(182),
            lossofMultiframeHigherOrderPath(183),
            lossOfPointerLowerOrderPath(184),
            lossOfPointerHigherOrderPath(185),
            losAttProgress(186),
            lossOsc(187),
            gfpLossOfClientSig(188),
            loopbackError(189),
            facilityLoopback(190),
            lossofTandemConnectionOduTcmA(191),
            lossofTandemConnectionOduTcmB(192),
            lossofTandemConnectionOduTcmC(193),
            mansw(194),
            equipmentNotAccepted(197),
            equipmentNotApproved(198),
            capabilityLevelMismatch(199),
            equipmentMismatch(200),
            equipmentNotSupportedByPhysicalLayer(201),
            meaSwRevision(202),
            mismatch(203),
            midstageFault(204),
            multiplexStructureIdentifierMismatchOPU(205),
            backupNotResponding(206),
            openConnectionIndicationOdu(207),
            openConnectionIndicationOduTcmA(208),
            openConnectionIndicationOduTcmB(209),
            openConnectionIndicationOduTcmC(210),
            oduTribMsiMismatch(211),
            transmitterDisabledOff(212),
            receiverDisabled(213),
            opmAbnormalCondition(214),
            faultOnOpm(215),
            thresOptPowerCtrlFailureHigh(216),
            thresOptPowerCtrlFailureLow(217),
            txPowerLimited(218),
            oscOpticalPowerControlFailHigh(219),
            oscOpticalPowerControlFailLow(220),
            oTDRMeasuringinProgress(221),
            encryptionModuleCryPasswdError(222),
            peerLink(223),
            pilotReceiveLevelHigh(224),
            lossOfPilotSignal(225),
            payloadMismatchGfp(226),
            payloadMismatchLowerOrderPath(227),
            payloadMismatchOPU(228),
            payloadMismatchHigherOrderPath(229),
            provPayloadMismatch(230),
            prbsLossOfSeqSynch(231),
            prbsRcvActivated(232),
            prbsTrmtActivated(233),
            protectionNotAvailable(234),
            powerSupplyUnitFailure(235),
            maxPowerConsProvModulesToHigh(236),
            maxPowerConsEquipModulesToHigh(237),
            powerMissing(238),
            remoteDefectIndicationLine(239),
            remoteDefectIndicationLowerOrderPath(240),
            remoteDefectIndicationHigherOrderPath(241),
            dcnCommunicationFail(243),
            ntpForSchedEqlzRequired(244),
            signalDegradeOlm(245),
            signalDegradeLine(246),
            signalDegradationonLinkVector(247),
            signalDegradeOdu(248),
            signalDegradeOtu(249),
            pcsSignalDegrade(250),
            signalDegradeScn(251),
            signalDegradeOduTcmA(252),
            signalDegradeOduTcmB(253),
            signalDegradeOduTcmC(254),
            moduleSelfTestFail(255),
            moduleSelfTestFailCritical(256),
            signalFailureOnLink(257),
            signalFailureonLinkVector(258),
            signalFailureOPU(259),
            clientOutage(260),
            facilityDataRateNotSupported(261),
            lossofSequenceLowerOrderPath(263),
            lossofSequenceHigherOrderPath(264),
            serverSignalFail(265),
            serverSignalFailureGfp(266),
            serverSignalFailureODU(267),
            serverSignalFailurePath(268),
            serverSignalFailureSectionRS(269),
            switchToDuplexInhibited(272),
            switchFailed(274),
            currentTooHigh(276),
            attOnReceiverFiberHigherThanMonitor(277),
            attOnReceiverFiberLowerThanMonitor(278),
            attOnTransmitterFiberHigherThanMonitor(279),
            attOnTransmitterFiberLowerThanMonitor(280),
            thres15MinExceededOduBbe(281),
            thres15MinExceededOtuBbe(283),
            thres15MinExceededOduTcmABbe(285),
            thres15MinExceededOduTcmBBbe(287),
            thres15MinExceededOduTcmCBbe(289),
            thres15MinExceededFecBERCE(291),
            brPwrRxTooHigh(293),
            chromaticDispersionTooHigh(294),
            chromaticDispersionTooLow(295),
            dispersionCompensationTooHigh(296),
            dispersionCompensationTooLow(297),
            thres15MinExceededFecCE(298),
            carrierFreqOffsetTooHigh(300),
            carrierFreqOffsetTooLow(301),
            thres15MinExceededSonetLineCV(302),
            thres15MinExceededPhysConvCV(304),
            thres15MinExceededSonetSectCV(306),
            thres15MinExceededPhysConvDE(308),
            differentialGroupDelayTooHigh(310),
            thres15MinExceededFecES(311),
            thres15MinExceededSonetLineES(313),
            thres15MinExceededOduES(315),
            thres15MinExceededOtuES(317),
            thres15MinExceededPhysConvES(319),
            thres15MinExceededSonetSectES(321),
            thres15MinExceededOduTcmAES(323),
            thres15MinExceededOduTcmBES(325),
            thres15MinExceededOduTcmCES(327),
            latencyTooHigh(329),
            latencyTooLow(330),
            laserBiasCurrentNormalizedtooHigh(331),
            localOscTemperatureTooHigh(332),
            localOscTemperatureTooLow(333),
            pumpLaser1TempTooHigh(334),
            pumpLaser1TempTooLow(335),
            pumpLaser2TempTooHigh(336),
            pumpLaser2TempTooLow(337),
            pumpLaser3TempTooHigh(338),
            pumpLaser3TempTooLow(339),
            pumpLaser4TempTooHigh(340),
            pumpLaser4TempTooLow(341),
            oscPwrTooHigh(342),
            oscPwrTooLow(343),
            ramanPumpPwrTooHigh(344),
            ramanPumpPwrTooLow(345),
            roundTripDelayTooHigh(346),
            roundTripDelayTooLow(347),
            thres15MinExceededSonetSectSEFS(348),
            thres15MinExceededFecSES(350),
            thres15MinExceededSonetLineSES(352),
            thres15MinExceededOduSES(354),
            thres15MinExceededOtuSES(356),
            thres15MinExceededSonetSectSES(358),
            thres15MinExceededOduTcmASES(360),
            thres15MinExceededOduTcmBSES(362),
            thres15MinExceededOduTcmCSES(364),
            logicalLanesSkewTooHigh(366),
            signalToNoiseRatioTooLow(367),
            subModuleTempTooHigh(368),
            temperatureTooHigh(369),
            temperatureTooLow(370),
            thres15MinExceededSonetLineUAS(371),
            thres15MinExceededOduUAS(373),
            thres15MinExceededOtuUAS(375),
            thres15MinExceededOduTcmAUAS(377),
            thres15MinExceededOduTcmBUAS(379),
            thres15MinExceededOduTcmCUAS(381),
            thres15MinExceededFecUBE(383),
            encryptionModuleTamperDetected(385),
            thermoElectricCoolerEndOfLife(386),
            inputTIF(387),
            traceIdentifierMismatchOdu(389),
            traceIdentifierMismatchOtu(390),
            sectionTraceMismatch(391),
            traceIdentifierMismatchOduTcmA(392),
            traceIdentifierMismatchOduTcmB(393),
            traceIdentifierMismatchOduTcmC(394),
            turnupFailed(395),
            turnupCondition(396),
            unequippedLowerOrderPath(397),
            unequippedHigherOrderPath(398),
            voaControlFail(399),
            voltageOutOfRange(400),
            inputVoltageFailure(401),
            inputVoltageFailurePort1(402),
            inputVoltageFailurePort2(403),
            wtrTimerRunning(406),
            lossOfLaneOtu(407),
            lossOfTestSeqSynchOpu(408),
            lossOfMfiOpu(409),
            oosDisabledLckOduTrmt(410),
            configurationMismatch(411),
            oduAutoShutdownRxAIS(412),
            oduAutoShutdownTxAIS(413),
            oosDisabledLckOduRx(414),
            thres15MinExceededBbePcs(420),
            autoShutdownGAis(422),
            equipmentMismatchAllow(423),
            warmUp(424),
            networkPathRestricted(432),
            vfClientSignalFail(434),
            autoShutdownVfCSF(435),
            linkFailToPartner1(439),
            linkFailToPartner2(440),
            linkFailToPartner3(441),
            linkFailToPartner4(442),
            partnerUnavailable(443),
            partner1Deleted(445),
            partner2Deleted(446),
            partner3Deleted(447),
            partner4Deleted(448),
            thres15MinExceededPhysConvSE(450),
            thres15MinExceededPhysConvCVDE(452),
            autoShutdownSendingOciOduTx(456),
            acpLinkLoss(457),
            acpChannelUnAvail(458),
            acpPartnerUnassigned(459),
            acpPartnerDeleted(460),
            thres15MinExceededCrcErrorsRcv(461),
            thres15MinExceededCrcFramesEgress(463),
            autoServiceMismatch(465),
            batteryNoCharge(466),
            tagReceiveFail(469),
            tagReceiveFailMaxReached(470),
            internalEncryptionFail(473),
            insufficientPower(476),
            powerConsumptionHigh(477),
            lossOfOverhead(478),
            lossOfInputSignal(479),
            otuServerSignalFail(480),
            lossOfAlignment(482),
            localFaultRx(483),
            localFaultTx(484),
            serverSignalFailRx(485),
            serverSignalFailTx(486),
            lossOfBlockLock(487),
            inputVoltageLow(488),
            outputVoltageFailure(489),
            outputPowerHigh(490),
            communicationLoss(491),
            incompatibleVersion(492),
            airDustFilterClogged(493),
            psmRedundancyMismatch(494),
            lossOfModemSync(495),
            serverSignalFailPayload(496),
            outputCurrentDrawHigh(497),
            rAndCPortOutage(498),
            rPortOutage(499),
            pPortOutage(500),
            hwOptReachedHT(501),
            excessLLDPNeighborsRx(502),
            excessLLDPNeighborsTx(503),
            configurationFault(504),
            channelMismatchRx(505),
            lossOfCoupling(506),
            hardwareUnavailable(507),
            cryAuthKeyMissing(511),
            cryDataInvalid(512),
            lossOfSignalDcPort(513),
            ampDisabled(514),
            licenseMissing(516),
            hwConfigFault(517),
            thres15MinExceededSonetSectBbe(518),
            thres15MinExceededSonetLineBbe(520),
            serverSignalFailLine(522),
            thres15MinExceededSonetSectOofs(523),
            noLicenseFile(525),
            licenseServerDisconnected(526),
            licenseServerNotConfigured(527),
            licenseInvalid(528),
            licenseOverdraft(529),
            licenseMissingMismatch(530),
            qualityFactorTooLow(531),
            replaceAirFilter(537),
            autoShutdownSendingIdle(538),
            mpFileMissing(541),
            delayMeasurementProgress(546),
            oprSignalDegrade(549),
            licenseBkServerDisconnected(550),
            rebootInProgress(551),
            qkdConnectionFail(554),
            qkdBackplaneFail(555),
            qkdInternalFail(556),
            qkdKeyLowRate(557),
            qkdNoKey(558),
            qkdConfError(559),
            opticalSignalToNoiseTooLow(561),
            stateOfPolarizationTooHigh(562),
            cdCompensationFail(563),
            pumpCurrentHigh(564),
            pumpCurrentAbnormal(565),
            pumpCurrentLow(566),
            opticalInputPowerHigh(567),
            scepError(568),
            caAuthPending(571),
            caAuthFailed(572),
            caTrustFailed(573),
            keyGenInProgress(576),
            keyGenFailed(577),
            keyRenewalInProgress(580),
            keyRenewalFailed(581),
            certReqInProgress(584),
            certReqFailed(585),
            certIssuerError(586),
            certDateInvalid(587),
            certRevoked(588),
            certSignatureInvalid(589),
            certAttributeInvalid(590),
            certConstraintsFail(591),
            certInvalid(592),
            crlFail(593),
            crlUpdatePending(594),
            crlUpdateFail(595),
            certActivationFailed(598),
            notOperationalSequence(599),
            encryptionCommMismatch(600),
            licenseExpiresIn28Days(606),
            licenseExpiresIn7Days(607),
            commDegraded(608),
            licenseServerTimeOutOfSync(612),
            modAuthPkiInternalFail(614),
            modAuthPkiCertUpdateFail(615),
            modAuthPkiConfigMismatch(616),
            modAuthPkiPairingFail(617),
            modAuthPkiPortsNotPaired(618),
            modAuthPkiCertRetrievalFail(619),
            spanEqualizationFault(620),
            componentTemperatureHigh(621),
            protectionCommandApplied(622),
            serverSignalFailureTcmA(623),
            serverSignalFailureTcmB(624),
            serverSignalFailureTcmC(625),
            passwordMismatch(626),
            passwordChangeFail(627),
            hwBusy(628),
            licenseConnInvalid(629),
            prbsLossOfSeqSynchLane1(631),
            prbsLossOfSeqSynchLane2(632),
            prbsLossOfSeqSynchLane3(633),
            prbsLossOfSeqSynchLane4(634),
            insecureProtocolActive(641),
            certActInProgress(642),
            sequentialFwpUpdateFail(643),
            laserBiasCurrUnstable(644),
            entropyUpdateFail(645),
            linkFailToOSCPartner(646),
            inhibitAuto(647),
            flexoGroupIdentMismatch(648),
            flexoMapMismatch(649),
            flexoRemoteDefectInd(650),
            otuLossOfFrameMultiFrame(651),
            flexoServerSignalFailure(652),
            tailEndCommFail(653),
            keyPairActFail(654),
            componentTemperatureWarn(655),
            componentTemperatureSd(656),
            cryptoServiceMissing(657),
            opticalBandwidthMismatch(658),
            allLanesSummaryOutage(659),
            eepromReadFail(660),
            psmProtectFault(661),
            notEnoughPsmPower(662),
            plugCommunicationFail(663),
            appletNotInstalled(670),
            appletNotConfigured(671),
            appletPinInvalid(672),
            certExpirationWarning(677),
            ntpAuthenticationFail(678),
            webClientAuthFail(681),
            certFailRequirement(682),
            oosDisabledSpeq(120000),
            oosMaintenanceSpeq(120002),
            messageLossSpeq(120004),
            oscFiberMissingSpeq(120005),
            optLowSpeq(120006),
            ppcOutOfRangeSpeq(120007),
            gainTooHighSpeq(120008),
            gainTooLowSpeq(120009),
            gainAdoptFailedSpeq(120010),
            processLockedOutSpeq(120011),
            ppcLimitExceededSpeq(120012)
        }

FspR7AlsMode ::= TEXTUAL-CONVENTION
  STATUS        current
  DESCRIPTION
        "Determines the reaction in backward direction in response to a LOS
        on the same Interface: on a Network Interface connected to the DWDM
        this is a matter of laser safety"
  SYNTAX    INTEGER
        {
            undefined(0),
            advaALS(1), --ALS is implemented on a Network-Side facility in backward direction to ensure laser safety
            sonetALS(2), --Typical of Client-Side behavior, - where so desired, - with long laser pulses but without ensuring laser safety if on the network side
            noALS(3), --Typical of Client-Side behavior, - where so desired, - without ensuring laser safety if on the network side
            fastAls(4) --Fast ALS; special quick version of SDH-ALS generally applied to the network port
        }

FspR7AlsModeCaps ::= TEXTUAL-CONVENTION
  STATUS        current
  DESCRIPTION
        "Determines the reaction in backward direction in response to a LOS
        on the same Interface: on a Network Interface connected to the DWDM
        this is a matter of laser safety"
  SYNTAX    BITS
        {
            capUndefined(0),
            capAdvaALS(1),
            capSonetALS(2),
            capNoALS(3),
            capFastAls(4)
        }

FspR7AppType ::= TEXTUAL-CONVENTION
  STATUS        current
  DESCRIPTION
        "Type of the application that sends trap."
  SYNTAX    INTEGER
        {
            undefined(0),
            lct(1),
            snmp(2),
            tl1(3),
            tcli(4),
            controlplane(5),
            system(6)
        }

FspR7ApsChannel ::= TEXTUAL-CONVENTION
  STATUS        current
  DESCRIPTION
        "Selection of the location of the APS channel"
  SYNTAX    INTEGER
        {
            undefined(0),
            none(1), --Protection operates without an APS Channel
            line(2), --Protection uses the MS-OH K1/K2 APS Bytes as APS Channel
            path(3), --Protection uses the POH K3 APS Bytes as APS Channel
            pm(4), --Protection uses the ODUk Path APS Channel
            tcm1(5), --Protection uses the ODUk TCM1 APS Channel
            tcm2(6), --Protection uses the ODUk TCM2 APS Channel
            tcm3(7), --Protection uses the ODUk TCM3 APS Channel
            tcm4(8), --Protection uses the ODUk TCM4 APS Channel
            tcm5(9), --Protection uses the ODUk TCM5 APS Channel
            tcm6(10), --Protection uses the ODUk TCM6 APS Channel
            sm(11), --Protection uses the ODUk Server APS Channel
            gfp(12), --Protection uses GFP Client Management Frames as APS Channel
            prop(13) --ADVA proprietary/ Not standardized
        }

FspR7APSCommand ::= TEXTUAL-CONVENTION
  STATUS        current
  DESCRIPTION
        "Protection Switch commands: Manual or Release.
        The 'Manual Switch' switches manually from addressed facility to
        the partner but does not force the traffic onto a broken fiber and
        it does not block the subsequent automatic functioning of the switch.
        The 'Release Switch' releases the current switch command.
        For 'Manual Switch' relevant only if revertivity is supported."
  SYNTAX    INTEGER
        {
            undefined(0),
            release(1),
            manualSwitch(2),
            clear(3),
            exercise(13),
            manualSwitchToWorking(15),
            manualSwitchToProtect(16),
            forcedSwitchToProtect(20),
            forcedSwitchToWorking(21),
            lockout(23)
        }

FspR7APSCommandCaps ::= TEXTUAL-CONVENTION
  STATUS        current
  DESCRIPTION
        "Protection Switch commands: Manual or Release.
        The 'Manual Switch' switches manually from addressed facility to
        the partner but does not force the traffic onto a broken fiber and
        it does not block the subsequent automatic functioning of the switch.
        The 'Release Switch' releases the current switch command.
        For 'Manual Switch' relevant only if revertivity is supported."
  SYNTAX    BITS
        {
            capUndefined(0),
            capRelease(1),
            capManualSwitch(2),
            capClear(3),
            capExercise(13),
            capManualSwitchToWorking(15),
            capManualSwitchToProtect(16),
            capForcedSwitchToProtect(20),
            capForcedSwitchToWorking(21),
            capLockout(23)
        }

FspR7ApsFarEndModule ::= TEXTUAL-CONVENTION
  STATUS        current
  DESCRIPTION
        "APS Far End Module"
  SYNTAX    INTEGER
        {
            undefined(0),
            eqp10tcc10g(1),
            other(2)
        }

FspR7ApsFarEndModuleCaps ::= TEXTUAL-CONVENTION
  STATUS        current
  DESCRIPTION
        "APS Far End Module"
  SYNTAX    BITS
        {
            capUndefined(0),
            capEqp10tcc10g(1),
            capOther(2)
        }

FspR7EquipmentAssignState ::= TEXTUAL-CONVENTION
  STATUS        current
  DESCRIPTION
        ""
  SYNTAX    INTEGER
        {
            undefined(0),
            assigned(1),
            assignable(2),
            notAssignable(3)
        }

FspR7AutosrvLock ::= TEXTUAL-CONVENTION
  STATUS        current
  DESCRIPTION
        "Facility Rate the Adaptive Clock detected and locked too."
  SYNTAX    INTEGER
        {
            undefined(0),
            none(1),
            ifTypeF270(2),
            ifTypeF1483(3),
            ifTypeF1485(4),
            ifTypeF2967(5),
            ifTypeF2970(6)
        }

FspR7Baund ::= TEXTUAL-CONVENTION
  STATUS        current
  DESCRIPTION
        "Baud rate of the serial interface"
  SYNTAX    INTEGER
        {
            undefined(0),
            baud2400(1),
            baud4800(2),
            baud9600(3),
            baud19200(4),
            baud38400(5),
            baud57600(6),
            baud115200(7)
        }

FspR7BaundCaps ::= TEXTUAL-CONVENTION
  STATUS        current
  DESCRIPTION
        "Baud rate of the serial interface"
  SYNTAX    BITS
        {
            capUndefined(0),
            capBaud2400(1),
            capBaud4800(2),
            capBaud9600(3),
            capBaud19200(4),
            capBaud38400(5),
            capBaud57600(6),
            capBaud115200(7)
        }

FspR7BERThreshold ::= TEXTUAL-CONVENTION
  STATUS        current
  DESCRIPTION
        "Bit-Error-Based Degradation Definition for SONET (standard integration period)"
  SYNTAX    INTEGER
        {
            undefined(0),
            exp5(1),
            exp6(2),
            exp7(3),
            exp8(4),
            exp9(5)
        }

FspR7BERThresholdCaps ::= TEXTUAL-CONVENTION
  STATUS        current
  DESCRIPTION
        "Bit-Error-Based Degradation Definition for SONET (standard integration period)"
  SYNTAX    BITS
        {
            capUndefined(0),
            capExp5(1),
            capExp6(2),
            capExp7(3),
            capExp8(4),
            capExp9(5)
        }

FspR7BidirectionalChannel ::= TEXTUAL-CONVENTION
  STATUS        current
  DESCRIPTION
        "Bidirectional Channel Rates from Provisioning"
  SYNTAX    INTEGER
        {
            undefined(0),
            tx1310rx1490(1), --Tx:1310nm, 228,85THz; Rx:1490nm, 201,20THz
            tx1490rx1310(2), --Tx:1490nm, 201,20THz; Rx:1310nm, 228,85THz
            tx1310rx1550(3), --Tx:1310nm, 228,85THz; Rx:1550nm, 193,41THz
            tx1550rx1310(4), --Tx:1550nm, 193,41THz; Rx:1310nm, 228,85THz
            tx1270rx1330(5), --Tx:1270nm, 236,06THz; Rx:1330nm, 225,41THz
            tx1330rx1270(6), --Tx:1330nm, 225,41THz; Rx:1270nm, 236,06THz
            tx1266rx1275(7), --Tx:1266nm, 236,80THz; Rx:1275nm, 235,13THz
            tx1275rx1266(8), --Tx:1275nm, 235,13THz; Rx:1266nm, 236,80THz
            tx1286rx1295(9), --Tx:1286nm, 233,12THz; Rx:1295nm, 231,50THz
            tx1295rx1286(10), --Tx:1295nm, 231,50THz; Rx:1286nm, 233,12THz
            tx1306rx1315(11), --Tx:1306nm, 229,55THz; Rx:1315nm, 227,98THz
            tx1315tx1306(12), --Tx:1315nm, 227,98THz; Rx:1306nm, 229,55THz
            tx1326rx1335(13), --Tx:1326nm, 226,09THz; Rx:1335nm, 224,56THz
            tx1335rx1326(14), --Tx:1335nm, 224,56THz; Rx:1326nm, 226,09THz
            tx1346rx1355(15), --Tx:1346nm, 222,73THz; Rx:1355nm, 221,25THz
            tx1355rx1346(16), --Tx:1355nm, 221,25THz; Rx:1346nm, 222,73THz
            tx1366rx1375(17), --Tx:1366nm, 219,47THz; Rx:1375nm, 218,03THz
            tx1375rx1366(18), --Tx:1375nm, 218,03THz; Rx:1366nm, 219,47THz
            tx1426rx1435(19), --Tx:1426nm, 210,23THz; Rx:1435nm, 208,91THz
            tx1435rx1426(20), --Tx:1435nm, 208,91THz; Rx:1426nm, 210,23THz
            tx1446rx1455(21), --Tx:1446nm, 207,33THz; Rx:1455nm, 206,04THz
            tx1455rx1446(22), --Tx:1455nm, 206,04THz; Rx:1446nm, 207,33THz
            tx1466rx1475(23), --Tx:1466nm, 204,50THz; Rx:1475nm, 203,25THz
            tx1475rx1466(24), --Tx:1475nm, 203,25THz; Rx:1466nm, 204,50THz
            tx1486rx1495(25), --Tx:1486nm, 201,74THz; Rx:1495nm, 200,53THz
            tx1495rx1486(26), --Tx:1495nm, 200,53THz; Rx:1486nm, 201,74THz
            tx1506rx1515(27), --Tx:1506nm, 199,07THz; Rx:1515nm, 197,88THz
            tx1515rx1506(28), --Tx:1515nm, 197,88THz; Rx:1506nm, 199,07THz
            tx1526rx1535(29), --Tx:1526nm, 196,46THz; Rx:1535nm, 195,30THz
            tx1535rx1526(30), --Tx:1535nm, 195,30THz; Rx:1526nm, 196,46THz
            tx1546rx1555(31), --Tx:1546nm, 193,91THz; Rx:1555nm, 192,79THz
            tx1555rx1546(32), --Tx:1555nm, 192,79THz; Rx:1546nm, 193,91THz
            tx1566rx1575(33), --Tx:1566nm, 191,44THz; Rx:1575nm, 190,34THz
            tx1575rx1566(34), --Tx:1575nm, 190,34THz; Rx:1566nm, 191,44THz
            tx1586rx1595(35), --Tx:1586nm, 189,02THz; Rx:1595nm, 187,96THz
            tx1595rx1586(36), --Tx:1595nm, 187,96THz; Rx:1586nm, 189,02THz
            tx1606rx1615(37), --Tx:1606nm, 186,67THz; Rx:1615nm, 185,63THz
            tx1615rx1606(38), --Tx:1615nm, 185,63THz; Rx:1606nm, 186,67THz
            tx1490rx1550(39), --Tx:1490nm, 201,20THz; Rx:1550nm, 193,40THz
            tx1550rx1490(40), --Tx:1550nm, 193,40THz; Rx:1490nm,  201,20THz
            tx850rx900(41), --Tx:850nm; Rx:900nm
            tx900rx850(42), --Tx:900nm; Rx:850nm
            g850g900(43) --G850 & G900
        }

FspR7BidirectionalChannelCaps ::= TEXTUAL-CONVENTION
  STATUS        current
  DESCRIPTION
        "Bidirectional Channel Rates from Provisioning"
  SYNTAX    BITS
        {
            capUndefined(0),
            capTx1310rx1490(1),
            capTx1490rx1310(2),
            capTx1310rx1550(3),
            capTx1550rx1310(4),
            capTx1270rx1330(5),
            capTx1330rx1270(6),
            capTx1266rx1275(7),
            capTx1275rx1266(8),
            capTx1286rx1295(9),
            capTx1295rx1286(10),
            capTx1306rx1315(11),
            capTx1315tx1306(12),
            capTx1326rx1335(13),
            capTx1335rx1326(14),
            capTx1346rx1355(15),
            capTx1355rx1346(16),
            capTx1366rx1375(17),
            capTx1375rx1366(18),
            capTx1426rx1435(19),
            capTx1435rx1426(20),
            capTx1446rx1455(21),
            capTx1455rx1446(22),
            capTx1466rx1475(23),
            capTx1475rx1466(24),
            capTx1486rx1495(25),
            capTx1495rx1486(26),
            capTx1506rx1515(27),
            capTx1515rx1506(28),
            capTx1526rx1535(29),
            capTx1535rx1526(30),
            capTx1546rx1555(31),
            capTx1555rx1546(32),
            capTx1566rx1575(33),
            capTx1575rx1566(34),
            capTx1586rx1595(35),
            capTx1595rx1586(36),
            capTx1606rx1615(37),
            capTx1615rx1606(38),
            capTx1490rx1550(39),
            capTx1550rx1490(40),
            capTx850rx900(41),
            capTx900rx850(42),
            capG850g900(43)
        }

FspR7Bitrate ::= TEXTUAL-CONVENTION
  STATUS        current
  DESCRIPTION
        "Provisioned data rate"
  SYNTAX    INTEGER
        {
            undefined(0),
            bitrate10(1),
            bitrate100(2),
            bitrate1000(3),
            bitrate10000(4)
        }

FspR7BitrateCaps ::= TEXTUAL-CONVENTION
  STATUS        current
  DESCRIPTION
        "Provisioned data rate"
  SYNTAX    BITS
        {
            capUndefined(0),
            capBitrate10(1),
            capBitrate100(2),
            capBitrate1000(3),
            capBitrate10000(4)
        }

FspR7CaAuthStatus ::= TEXTUAL-CONVENTION
  STATUS        current
  DESCRIPTION
        "Status of CA authentication procedure, i.e. obtaining, installing and verifying CA issuing certificate(s)."
  SYNTAX    INTEGER
        {
            undefined(0),
            none(1), --CA authentication procedure has not been initiated yet (valid status), i.e. no CA certificate(s) are installed.
            okay(2),
            pending(3),
            resourceError(4), --Failed to install obtained CA certificate(s) due to resource restrictions.
            scepError(5), --Failed to obtain CA certificate(s) due to SCEP (communication) error; reason for failure is indicated in SCEP-STATUS-LIST.
            certError(6), --Failed to verify obtained CA certificate(s); possibly some obtained CA certificate(s) is not valid or is not even a CA issuing certificate.
            generalFail(7), --Failed to either obtain, install or verify CA certificate(s); generic (unexpected) error.
            authorityNotTrusted(8), --Failed to verify installed CA certificate(s); install missing CA certificate and/or set one to trusted.
            busyError(9), --Failued to either obtain, install or verify CA certificates(s) due to busy local resources; may try again later.
            attributeError(10), --IDEA. Failed to verify obtained/installed CA certificate(s); possibly some installed certificate(s) is not a valid CA issuing certificate.
            issuerNotKnown(11), --IDEA. CA certificate(s) error, because issuer is not known; some missing CA certificate needs to be installed.
            issuerNotTrusted(12) --IDEA. CA certificate(s) error, because of issuer is not trusted; some installed CA certificate needs to be set as trusted.
        }

FspR7CapInventory ::= TEXTUAL-CONVENTION
  STATUS        current
  DESCRIPTION
        "Capability level reported by HW"
  SYNTAX    INTEGER
        {
            undefined(0),
            level0(1), --This level represents the basic functionality;
            level1(2),
            level2(3),
            level3(4),
            level4(5),
            level5(6),
            unknown(50) --This level represents the functionality unknown to system;
        }

FspR7CapInventoryCaps ::= TEXTUAL-CONVENTION
  STATUS        current
  DESCRIPTION
        "Capability level reported by HW"
  SYNTAX    BITS
        {
            capUndefined(0),
            capLevel0(1),
            capLevel1(2),
            capLevel2(3),
            capLevel3(4),
            capLevel4(5),
            capLevel5(6),
            capUnknown(50)
        }

FspR7Category ::= TEXTUAL-CONVENTION
  STATUS        current
  DESCRIPTION
        "Used For Internal Purposes (and possibly for pre-selection in GUI)"
  SYNTAX    INTEGER
        {
            undefined(0),
            shelf(1),
            channelMod(2),
            plug(3),
            filter(4),
            amplifier(5),
            dcm(6),
            switch(7),
            oscm(8),
            dummy(9),
            common(10),
            att(11),
            jumper(12),
            accessory(13),
            fiber(14),
            protectionMod(15),
            any(16),
            roadm(17),
            ethernetMod(18),
            powerSplitter(19),
            adm(20),
            xc(21),
            mon(22),
            protectionCab(23),
            filterCab(24),
            laserBnk(25),
            microTerm(26),
            microAmp(27),
            pathSplitter(30)
        }

FspR7CaTrustStatus ::= TEXTUAL-CONVENTION
  STATUS        current
  DESCRIPTION
        "Installed CA certificates trust status"
  SYNTAX    INTEGER
        {
            undefined(0),
            none(1), --CA certificates have not been installed.
            caNotTrusted(2), --None of installed CA certificate(s) is trusted.
            caTrusted(3), --Some of installed CA certificate(s), either the root or an intermediate issuing certficate, is trusted.
            certError(4), --Installed CA certificate(s) error; possibly some certificate is not valid or not even an issuing certificate.
            generalFail(5) --Evaluation of trust status failed, because of generic (unexpected) error.
        }

FspR7CdCompensationRange ::= TEXTUAL-CONVENTION
  STATUS        current
  DESCRIPTION
        "Chromatic Dispersion Compensation Goal"
  SYNTAX    INTEGER
        {
            undefined(0),
            highCDC(1),
            lowSw(2)
        }

FspR7CdCompensationRangeCaps ::= TEXTUAL-CONVENTION
  STATUS        current
  DESCRIPTION
        "Chromatic Dispersion Compensation Goal"
  SYNTAX    BITS
        {
            capUndefined(0),
            capHighCDC(1),
            capLowSw(2)
        }

FspR7CdPostCompensationRange ::= TEXTUAL-CONVENTION
  STATUS        current
  DESCRIPTION
        "CD Post Compensation Range
        Range 1: [-22 ns/nm   to +6 ns/nm] or [-20 ns/nm to +2 ns/nm]
        Range 2: [-72 ns/nm   to +6 ns/nm] or [-45 ns/nm to +5 ns/nm]
        Range 3: [-120 ns/nm to +6 ns/nm]
        Range 4: [-280 ns/nm to +6 ns/nm]"
  SYNTAX    INTEGER
        {
            undefined(0),
            range1(1), --[-22 ns/nm to +6 ns/nm] or [-20 ns/nm to +2 ns/nm]
            range2(2), --[-72 ns/nm to +6 ns/nm] or [-45 ns/nm to +5 ns/nm]
            range3(3), --[-120 ns/nm to +6 ns/nm]
            range4(4) --[-280 ns/nm to +6 ns/nm]
        }

FspR7CdPostCompensationRangeCaps ::= TEXTUAL-CONVENTION
  STATUS        current
  DESCRIPTION
        "CD Post Compensation Range
        Range 1: [-22 ns/nm   to +6 ns/nm] or [-20 ns/nm to +2 ns/nm]
        Range 2: [-72 ns/nm   to +6 ns/nm] or [-45 ns/nm to +5 ns/nm]
        Range 3: [-120 ns/nm to +6 ns/nm]
        Range 4: [-280 ns/nm to +6 ns/nm]"
  SYNTAX    BITS
        {
            capUndefined(0),
            capRange1(1),
            capRange2(2),
            capRange3(3),
            capRange4(4)
        }

FspR7CertRenewInterval ::= TEXTUAL-CONVENTION
  STATUS        current
  DESCRIPTION
        "Public key certificate renewal interval. Determines when to renew certificate relative to current certificate's either validity period (when given in percentage) or validity end date (when given as time span)."
  SYNTAX    INTEGER
        {
            undefined(0),
            none(1), --Renewal interval is irrelevant, because of configured renewal mode being either manual or disabled altogether.
            byExpiration(100), --Set planned renewal data as close as (but not before) when a certificate expires
            renew15min(1015), --Set planned renewal date 15 minutes before a certificate expires
            renew30min(1030), --Set planned renewal date 30 minutes before a certificate expires
            renew45min(1045), --Renew certificate 45 minutes before a certificate expires
            userHour(2000), --Set planned renewal date user-provided arbitrary number of hours before a certificate expires. JUST AN IDEA
            renew1hour(2001), --Set planned renewal date 1 hour before a certificate expires
            renew3hours(2003), --Set planned renewal date 3 hours before a certificate expires
            renew6hours(2006), --Set planned renewal date 6 hours before a certificate expires
            renew12hours(2012), --Set planned renewal date 12 hours before a certificate expires
            renew24hours(2024), --Set planned renewal date 24 hours before a certificate expires
            userDay(3000), --Set planned renewal date user-provided arbitrary number of days before a certificate exires. JUST AN IDEA
            renew1day(3001), --Set planned renewal date one day before a certificate expires
            renew2days(3002), --Set planned renewal date 2 days before a certificate expires
            renew5days(3005), --Set planned renewal date 5 days before a certificate expires
            renew7days(3007), --Set planned renewal date one week before a certificate expires
            renew10days(3010), --Set planned renewal date 10 days before a certificate expires
            renew30days(3030), --Set planned renewal date 30 days before a certificate expires
            renew90days(3090), --Set planned renewal date 90 days before a certificate expires
            renew180days(3180) --Set planned renewal date 180 days before a certificate expires
        }

FspR7CertRenewMode ::= TEXTUAL-CONVENTION
  STATUS        current
  DESCRIPTION
        "Public key certificate renewal mode - either manual or automatic.
        In automatic mode, at every system startup, the system verifies the certificate and triggers generation of a new one if needed.
        In manual mode the user must trigger generation of a new certificate."
  SYNTAX    INTEGER
        {
            undefined(0),
            none(1), --Renewal of either key-pair or certificate, either manual or automatic, is disabled, because of configured key profile.
            automatic(2), --Automatically generate new key-pair and update certificate for the new public key.
            manual(3), --Manually generate new key-pair and update certificate for the new public key.
            automaticCert(4), --Keep current key-pair and automatically renew certificate for the current public key.
            manualCert(5) --Keep current key-pair and manually renew certificate for the current public key.
        }

FspR7CertRequestStatus ::= TEXTUAL-CONVENTION
  STATUS        current
  DESCRIPTION
        "Status of the last certificate signing request"
  SYNTAX    INTEGER
        {
            undefined(0),
            none(1), --Request procedure has not been initiated yet (valid status).
            okay(2),
            pending(3),
            resourcesError(4), --Failed to install end-entity certificate due to resource restrictions.
            scepError(5), --SCEP (communication) error; reason for failure is indicated in SCEP-STATUS-LIST.
            csrReady(6), --Certificate Signing Request (CSR) is ready to be provided manually to the CA/RA entity (relevant when not using SCEP).
            csrPending(7), --Request (CSR) is now waiting CA/RA entity to approve it (relevant when using SCEP).
            attributeError(8), --Request attribute is either invalid or missing.
            certError(9), --Issued certificate error; possibly issuing CA certificate(s) is/are not trusted.
            generalFail(10),
            caNotTrusted(11), --Issuing CA is not trusted; install CA certificate and/or set it to trusted.
            busyError(12) --Request procedure error, because of busy local resources; may try later.
        }

FspR7CertValidityPeriod ::= TEXTUAL-CONVENTION
  STATUS        current
  DESCRIPTION
        "Public key certificate requested validity period (in years)"
  SYNTAX    INTEGER
        {
            undefined(0),
            none(1000), --Validity period is irrelevant, because it is configured to request externally signed certificate, in which case validity period cannot be explicitly set or requested.
            userProvided(3000), --User-provided arbitrary number of days. JUST AN IDEA
            valid1day(3001),
            valid2days(3002),
            valid5days(3005),
            valid7days(3007),
            valid10days(3010),
            valid30days(3030),
            valid90days(3090),
            valid180days(3180),
            valid1year(6001),
            valid2years(6002),
            valid3years(6003),
            valid4years(6004),
            valid5years(6005)
        }

FspR7ChannelBandwidth ::= TEXTUAL-CONVENTION
  STATUS        current
  DESCRIPTION
        "Channel Bandwidth"
  SYNTAX    INTEGER
        {
            undefined(0),
            band50G(1),
            band75G(2),
            band100G(3),
            band125G(4),
            band150G(5),
            band175G(6),
            band200G(7),
            band225G(8),
            band250G(9),
            band275G(10),
            band300G(11),
            band20nm(12),
            band325G(13),
            band350G(14),
            band375G(15),
            band400G(16),
            band37G5(17),
            notDefined(18),
            band62G5(19),
            band87G5(20),
            band112G5(21),
            band137G5(22),
            band162G5(23),
            band187G5(24),
            band212G5(25),
            band237G5(26),
            band262G5(27),
            band287G5(28),
            band312G5(29),
            band337G5(30),
            band362G5(31),
            band387G5(32),
            band12G5(33)
        }

FspR7ChannelBandwidthCaps ::= TEXTUAL-CONVENTION
  STATUS        current
  DESCRIPTION
        "Channel Bandwidth"
  SYNTAX    BITS
        {
            capUndefined(0),
            capBand50G(1),
            capBand75G(2),
            capBand100G(3),
            capBand125G(4),
            capBand150G(5),
            capBand175G(6),
            capBand200G(7),
            capBand225G(8),
            capBand250G(9),
            capBand275G(10),
            capBand300G(11),
            capBand20nm(12),
            capBand325G(13),
            capBand350G(14),
            capBand375G(15),
            capBand400G(16),
            capBand37G5(17),
            capNotDefined(18),
            capBand62G5(19),
            capBand87G5(20),
            capBand112G5(21),
            capBand137G5(22),
            capBand162G5(23),
            capBand187G5(24),
            capBand212G5(25),
            capBand237G5(26),
            capBand262G5(27),
            capBand287G5(28),
            capBand312G5(29),
            capBand337G5(30),
            capBand362G5(31),
            capBand387G5(32),
            capBand12G5(33)
        }

FspR7ChannelIdentifier ::= TEXTUAL-CONVENTION
  STATUS        current
  DESCRIPTION
        "Channel"
  SYNTAX    INTEGER
        {
            undefined(0),
            d01(1), --196,00THz 1529,55nm
            d02(2), --195,90THz 1530,33nm
            d03(3), --195,80THz 1531,12nm
            d04(4), --195,70THz 1531,90nm
            d05(5), --195,50THz 1533,47nm
            d06(6), --195,40THz 1534,25nm
            d07(7), --195,30THz 1535,04nm
            d08(8), --195,20THz 1535,82nm
            d09(9), --195,00THz 1537,40nm
            d10(10), --194,90THz 1538,19nm
            d11(11), --194,80THz 1538,98nm
            d12(12), --194,70THz 1539,77nm
            d13(13), --194,50THz 1541,35nm
            d14(14), --194,40THz 1542,14nm
            d15(15), --194,30THz 1542,94nm
            d16(16), --194,20THz 1543,73nm
            d17(17), --193,80THz 1546,92nm
            d18(18), --193,70THz 1547,72nm
            d19(19), --193,60THz 1548,51nm
            d20(20), --193,50THz 1549,32nm
            d21(21), --193,30THz 1550,92nm
            d22(22), --193,20THz 1551,72nm
            d23(23), --193,10THz 1552,52nm
            d24(24), --193,00THz 1553,33nm
            d25(25), --192,80THz 1554,94nm
            d26(26), --192,70THz 1555,75nm
            d27(27), --192,60THz 1556,55nm
            d28(28), --192,50THz 1557,36nm
            d29(29), --192,30THz 1558,98nm
            d30(30), --192,20THz 1559,79nm
            d31(31), --192,10THz 1560,61nm
            d32(32), --192,00THz 1561,42nm
            d33(33), --191,00THz 1569,59nm
            d34(34), --190,90THz 1570,42nm
            d35(35), --190,80THz 1571,24nm
            d36(36), --190,70THz 1572,06nm
            d37(37), --190,50THz 1573,71nm
            d38(38), --190,40THz 1574,54nm
            d39(39), --190,30THz 1575,37nm
            d40(40), --190,20THz 1576,20nm
            d41(41), --190,00THz 1577,86nm
            d42(42), --189,90THz 1578,69nm
            d43(43), --189,80THz 1579,52nm
            d44(44), --189,70THz 1580,35nm
            d45(45), --189,50THz 1582,02nm
            d46(46), --189,40THz 1582,85nm
            d47(47), --189,30THz 1583,69nm
            d48(48), --189,20THz 1584,53nm
            d49(49), --188,80THz 1587,88nm
            d50(50), --188,70THz 1588,73nm
            d51(51), --188,60THz 1589,57nm
            d52(52), --188,50THz 1590,41nm
            d53(53), --188,30THz 1592,10nm
            d54(54), --188,20THz 1592,95nm
            d55(55), --188,10THz 1593,79nm
            d56(56), --188,00THz 1594,64nm
            d57(57), --187,80THz 1596,34nm
            d58(58), --187,70THz 1597,19nm
            d59(59), --187,60THz 1598,04nm
            d60(60), --187,50THz 1598,89nm
            d61(61), --187,30THz 1600,60nm
            d62(62), --187,20THz 1601,56nm
            d63(63), --187,10THz 1602,31nm
            d64(64), --187,00THz 1603,17nm
            dc1(65), --195,60THz 1532,68nm
            dc2(66), --195,10THz 1536,61nm
            dc3(67), --194,60THz 1540,56nm
            dc4(68), --194,10THz 1544,53nm
            dc5(69), --193,90THz 1546,12nm
            dc6(70), --193,40THz 1550,12nm
            dc7(71), --192,90THz 1554,13nm
            dc8(72), --192,40THz 1558,17nm
            dl1(73), --190,60THz 1572,89nm
            dl2(74), --190,10THz 1577,03nm
            dl3(75), --189,60THz 1581,18nm
            dl4(76), --189,10THz 1585,36nm
            dl5(77), --188,90THz 1587,04nm
            dl6(78), --188,40THz 1591,26nm
            dl7(79), --187,90THz 1595,49nm
            dl8(80), --187,40THz 1599,75nm
            dc9(81), --194,00THz 1545,322nm
            dl9(82), --189,00THz 1586,203nm
            f19640(83), --196.40THz 1526.44nm
            f19635(84), --196.35THz 1526.83nm
            f19630(85), --196.30THz 1527.22nm
            f19625(86), --196.25THz 1527.60nm
            f19620(87), --196.20THz 1527.99nm
            f19615(88), --196.15THz 1528.38nm
            f19605(89), --196.05THz 1529.16nm
            c1470(91), --1470,00nm
            c1490(92), --1490,00nm
            c1510(93), --1510,00nm
            c1530(94), --1530,00nm
            c1550(95), --1550,00nm
            c1570(96), --1570,00nm
            c1590(97), --1590,00nm
            c1610(98), --1610,00nm
            s1310(99), --1310,00nm OSC
            s1630(100), --1630,00nm OSC
            g850(101), --850,00nm
            g1310(102), --1310,00nm
            g1550(103), --1550,00nm
            -- any(104),
            notInGrid(105),
            s1510(106), --1510,00nm OSC
            f19610(107), --196,10THz  1528,7734nm
            f19595(108), --195,95THz  1529,9436nm
            f19585(109), --195,85THz  1530,7248nm
            f19575(110), --195,75THz  1531,5068nm
            f19565(111), --195,65THz  1532,2896nm
            f19555(112), --195,55THz  1533,0732nm
            f19545(113), --195,45THz  1533,8575nm
            f19535(114), --195,35THz  1534,6427nm
            f19525(115), --195,25THz  1535,4287nm
            f19515(116), --195,15THz  1536,2155nm
            f19505(117), --195,05THz  1537,0031nm
            f19495(118), --194,95THz  1537,7915nm
            f19485(119), --194,85THz  1538,5807nm
            f19475(120), --194,75THz  1539,3708nm
            f19465(121), --194,65THz  1540,1616nm
            f19455(122), --194,55THz  1540,9533nm
            f19445(123), --194,45THz  1541,7457nm
            f19435(124), --194,35THz  1542,5390nm
            f19425(125), --194,25THz  1543,3331nm
            f19415(126), --194,15THz  1544,1280nm
            f19405(127), --194,05THz  1544,9238nm
            f19395(128), --193,95THz  1545,7203nm
            f19385(129), --193,85THz  1546,5177nm
            f19375(130), --193,75THz  1547,3159nm
            f19365(131), --193,65THz  1548,1149nm
            f19355(132), --193,55THz  1548,9148nm
            f19345(133), --193,45THz  1549,7155nm
            f19335(134), --193,35THz  1550,5170nm
            f19325(135), --193,25THz  1551,3193nm
            f19315(136), --193,15THz  1552,1225nm
            f19305(137), --193,05THz  1552,9265nm
            f19295(138), --192,95THz  1553,7313nm
            f19285(139), --192,85THz  1554,5370nm
            f19275(140), --192,75THz  1555,3435nm
            f19265(141), --192,65THz  1556,1508nm
            f19255(142), --192,55THz  1556,9590nm
            f19245(143), --192,45THz  1557,7680nm
            f19235(144), --192,35THz  1558,5779nm
            f19225(145), --192,25THz  1559,3886nm
            f19215(146), --192,15THz  1560,2001nm
            f19205(147), --192,05THz  1561,0125nm
            f19600(148), --196,00THz 1529,55nm D01
            f19590(149), --195,90THz 1530,33nm D02
            f19580(150), --195,80THz 1531,12nm D03
            f19570(151), --195,70THz 1531,90nm D04
            f19560(152), --195,60THz 1532,68nm DC1
            f19550(153), --195,50THz 1533,47nm D05
            f19540(154), --195,40THz 1534,25nm D06
            f19530(155), --195,30THz 1535,04nm D07
            f19520(156), --195,20THz 1535,82nm D08
            f19510(157), --195,10THz 1536,60nm DC2
            f19500(158), --195,00THz 1537,40nm D09
            f19490(159), --194,90THz 1538,19nm D10
            f19480(160), --194,80THz 1538,98nm D11
            f19470(161), --194,70THz 1539,77nm D12
            f19460(162), --194,60THz 1540,55nm DC3
            f19450(163), --194,50THz 1541,35nm D13
            f19440(164), --194,40THz 1542,14nm D14
            f19430(165), --194,30THz 1542,94nm D15
            f19420(166), --194,20THz 1543,73nm D16
            f19410(167), --194,10THz 1544,52nm DC4
            f19400(168), --194,00THz 1545,32nm DC9
            f19390(169), --193,90THz 1546,11nm DC5
            f19380(170), --193,80THz 1546,92nm D17
            f19370(171), --193,70THz 1547,72nm D18
            f19360(172), --193,60THz 1548,51nm D19
            f19350(173), --193,50THz 1549,32nm D20
            f19340(174), --193,40THz 1550,11nm DC6
            f19330(175), --193,30THz 1550,92nm D21
            f19320(176), --193,20THz 1551,72nm D22
            f19310(177), --193,10THz 1552,52nm D23
            f19300(178), --193,00THz 1553,33nm D24
            f19290(179), --192,90THz 1554,13nm DC7
            f19280(180), --192,80THz 1554,94nm D25
            f19270(181), --192,70THz 1555,75nm D26
            f19260(182), --192,60THz 1556,55nm D27
            f19250(183), --192,50THz 1557,36nm D28
            f19240(184), --192,40THz 1558,17nm DC8
            f19230(185), --192,30THz 1558,98nm D29
            f19220(186), --192,20THz 1559,79nm D30
            f19210(187), --192,10THz 1560,61nm D31
            f19200(188), --192,00THz 1561,42nm D32
            c1270(189), --1270,00nm
            c1290(190), --1290,00nm
            c1310(191), --1310,00nm
            c1330(192), --1330,00nm
            c1350(193), --1350,00nm
            c1370(194), --1370,00nm
            c1430(195), --1430,00nm
            c1450(196), --1450,00nm
            s1610(197), --1610,00nm OSC
            t1650(198), --1650,00nm OTDR
            s1490(199), --1490,00nm OSC
            f19598(200), --195.9875THz , 1529.6509nm
            f19597(201), --195.975THz , 1529.7485nm
            f19596(202), --195.9625THz , 1529.8461nm
            f19593(203), --195.9375THz , 1530.0413nm
            f19592(204), --195.925THz , 1530.1389nm
            f19591(205), --195.9125THz , 1530.2365nm
            f19588(206), --195.8875THz , 1530.4318nm
            f19587(207), --195.875THz , 1530.5295nm
            f19586(208), --195.8625THz , 1530.6271nm
            f19583(209), --195.8375THz , 1530.8225nm
            f19582(210), --195.825THz , 1530.9203nm
            f19581(211), --195.8125THz , 1531.018nm
            f19578(212), --195.7875THz , 1531.2135nm
            f19577(213), --195.775THz , 1531.3112nm
            f19576(214), --195.7625THz , 1531.409nm
            f19573(215), --195.7375THz , 1531.6046nm
            f19572(216), --195.725THz , 1531.7024nm
            f19571(217), --195.7125THz , 1531.8003nm
            f19568(218), --195.6875THz , 1531.996nm
            f19567(219), --195.675THz , 1532.0938nm
            f19566(220), --195.6625THz , 1532.1917nm
            f19563(221), --195.6375THz , 1532.3875nm
            f19562(222), --195.625THz , 1532.4854nm
            f19561(223), --195.6125THz , 1532.5833nm
            f19558(224), --195.5875THz , 1532.7792nm
            f19557(225), --195.575THz , 1532.8772nm
            f19556(226), --195.5625THz , 1532.9752nm
            f19553(227), --195.5375THz , 1533.1712nm
            f19552(228), --195.525THz , 1533.2692nm
            f19551(229), --195.5125THz , 1533.3672nm
            f19548(230), --195.4875THz , 1533.5633nm
            f19547(231), --195.475THz , 1533.6614nm
            f19546(232), --195.4625THz , 1533.7595nm
            f19543(233), --195.4375THz , 1533.9557nm
            f19542(234), --195.425THz , 1534.0538nm
            f19541(235), --195.4125THz , 1534.1519nm
            f19538(236), --195.3875THz , 1534.3482nm
            f19537(237), --195.375THz , 1534.4464nm
            f19536(238), --195.3625THz , 1534.5445nm
            f19533(239), --195.3375THz , 1534.7409nm
            f19532(240), --195.325THz , 1534.8392nm
            f19531(241), --195.3125THz , 1534.9374nm
            f19528(242), --195.2875THz , 1535.1339nm
            f19527(243), --195.275THz , 1535.2321nm
            f19526(244), --195.2625THz , 1535.3304nm
            f19523(245), --195.2375THz , 1535.527nm
            f19522(246), --195.225THz , 1535.6253nm
            f19521(247), --195.2125THz , 1535.7237nm
            f19518(248), --195.1875THz , 1535.9204nm
            f19517(249), --195.175THz , 1536.0187nm
            f19516(250), --195.1625THz , 1536.1171nm
            f19513(251), --195.1375THz , 1536.3139nm
            f19512(252), --195.125THz , 1536.4123nm
            f19511(253), --195.1125THz , 1536.5108nm
            f19508(254), --195.0875THz , 1536.7077nm
            f19507(255), --195.075THz , 1536.8061nm
            f19506(256), --195.0625THz , 1536.9046nm
            f19503(257), --195.0375THz , 1537.1016nm
            f19502(258), --195.025THz , 1537.2001nm
            f19501(259), --195.0125THz , 1537.2987nm
            f19498(260), --194.9875THz , 1537.4958nm
            f19497(261), --194.975THz , 1537.5943nm
            f19496(262), --194.9625THz , 1537.6929nm
            f19493(263), --194.9375THz , 1537.8901nm
            f19492(264), --194.925THz , 1537.9888nm
            f19491(265), --194.9125THz , 1538.0874nm
            f19488(266), --194.8875THz , 1538.2847nm
            f19487(267), --194.875THz , 1538.3834nm
            f19486(268), --194.8625THz , 1538.482nm
            f19483(269), --194.8375THz , 1538.6795nm
            f19482(270), --194.825THz , 1538.7782nm
            f19481(271), --194.8125THz , 1538.8769nm
            f19478(272), --194.7875THz , 1539.0744nm
            f19477(273), --194.775THz , 1539.1732nm
            f19476(274), --194.7625THz , 1539.272nm
            f19473(275), --194.7375THz , 1539.4696nm
            f19472(276), --194.725THz , 1539.5684nm
            f19471(277), --194.7125THz , 1539.6672nm
            f19468(278), --194.6875THz , 1539.865nm
            f19467(279), --194.675THz , 1539.9638nm
            f19466(280), --194.6625THz , 1540.0627nm
            f19463(281), --194.6375THz , 1540.2605nm
            f19462(282), --194.625THz , 1540.3595nm
            f19461(283), --194.6125THz , 1540.4584nm
            f19458(284), --194.5875THz , 1540.6563nm
            f19457(285), --194.575THz , 1540.7553nm
            f19456(286), --194.5625THz , 1540.8543nm
            f19453(287), --194.5375THz , 1541.0523nm
            f19452(288), --194.525THz , 1541.1513nm
            f19451(289), --194.5125THz , 1541.2503nm
            f19448(290), --194.4875THz , 1541.4485nm
            f19447(291), --194.475THz , 1541.5475nm
            f19446(292), --194.4625THz , 1541.6466nm
            f19443(293), --194.4375THz , 1541.8448nm
            f19442(294), --194.425THz , 1541.944nm
            f19441(295), --194.4125THz , 1542.0431nm
            f19438(296), --194.3875THz , 1542.2414nm
            f19437(297), --194.375THz , 1542.3406nm
            f19436(298), --194.3625THz , 1542.4398nm
            f19433(299), --194.3375THz , 1542.6382nm
            f19432(300), --194.325THz , 1542.7375nm
            f19431(301), --194.3125THz , 1542.8367nm
            f19428(302), --194.2875THz , 1543.0352nm
            f19427(303), --194.275THz , 1543.1345nm
            f19426(304), --194.2625THz , 1543.2338nm
            f19423(305), --194.2375THz , 1543.4324nm
            f19422(306), --194.225THz , 1543.5318nm
            f19421(307), --194.2125THz , 1543.6311nm
            f19418(308), --194.1875THz , 1543.8298nm
            f19417(309), --194.175THz , 1543.9292nm
            f19416(310), --194.1625THz , 1544.0286nm
            f19413(311), --194.1375THz , 1544.2275nm
            f19412(312), --194.125THz , 1544.3269nm
            f19411(313), --194.1125THz , 1544.4263nm
            f19408(314), --194.0875THz , 1544.6253nm
            f19407(315), --194.075THz , 1544.7248nm
            f19406(316), --194.0625THz , 1544.8243nm
            f19403(317), --194.0375THz , 1545.0233nm
            f19402(318), --194.025THz , 1545.1228nm
            f19401(319), --194.0125THz , 1545.2224nm
            f19398(320), --193.9875THz , 1545.4215nm
            f19397(321), --193.975THz , 1545.5211nm
            f19396(322), --193.9625THz , 1545.6207nm
            f19393(323), --193.9375THz , 1545.82nm
            f19392(324), --193.925THz , 1545.9196nm
            f19391(325), --193.9125THz , 1546.0193nm
            f19388(326), --193.8875THz , 1546.2186nm
            f19387(327), --193.875THz , 1546.3183nm
            f19386(328), --193.8625THz , 1546.418nm
            f19383(329), --193.8375THz , 1546.6174nm
            f19382(330), --193.825THz , 1546.7172nm
            f19381(331), --193.8125THz , 1546.8169nm
            f19378(332), --193.7875THz , 1547.0165nm
            f19377(333), --193.775THz , 1547.1163nm
            f19376(334), --193.7625THz , 1547.2161nm
            f19373(335), --193.7375THz , 1547.4157nm
            f19372(336), --193.725THz , 1547.5156nm
            f19371(337), --193.7125THz , 1547.6155nm
            f19368(338), --193.6875THz , 1547.8152nm
            f19367(339), --193.675THz , 1547.9151nm
            f19366(340), --193.6625THz , 1548.015nm
            f19363(341), --193.6375THz , 1548.2149nm
            f19362(342), --193.625THz , 1548.3148nm
            f19361(343), --193.6125THz , 1548.4148nm
            f19358(344), --193.5875THz , 1548.6148nm
            f19357(345), --193.575THz , 1548.7148nm
            f19356(346), --193.5625THz , 1548.8148nm
            f19353(347), --193.5375THz , 1549.0148nm
            f19352(348), --193.525THz , 1549.1149nm
            f19351(349), --193.5125THz , 1549.2149nm
            f19348(350), --193.4875THz , 1549.4151nm
            f19347(351), --193.475THz , 1549.5152nm
            f19346(352), --193.4625THz , 1549.6153nm
            f19343(353), --193.4375THz , 1549.8156nm
            f19342(354), --193.425THz , 1549.9158nm
            f19341(355), --193.4125THz , 1550.0159nm
            f19338(356), --193.3875THz , 1550.2163nm
            f19337(357), --193.375THz , 1550.3165nm
            f19336(358), --193.3625THz , 1550.4167nm
            f19333(359), --193.3375THz , 1550.6172nm
            f19332(360), --193.325THz , 1550.7175nm
            f19331(361), --193.3125THz , 1550.8178nm
            f19328(362), --193.2875THz , 1551.0183nm
            f19327(363), --193.275THz , 1551.1187nm
            f19326(364), --193.2625THz , 1551.219nm
            f19323(365), --193.2375THz , 1551.4197nm
            f19322(366), --193.225THz , 1551.52nm
            f19321(367), --193.2125THz , 1551.6204nm
            f19318(368), --193.1875THz , 1551.8212nm
            f19317(369), --193.175THz , 1551.9216nm
            f19316(370), --193.1625THz , 1552.022nm
            f19313(371), --193.1375THz , 1552.2229nm
            f19312(372), --193.125THz , 1552.3234nm
            f19311(373), --193.1125THz , 1552.4239nm
            f19308(374), --193.0875THz , 1552.6249nm
            f19307(375), --193.075THz , 1552.7254nm
            f19306(376), --193.0625THz , 1552.8259nm
            f19303(377), --193.0375THz , 1553.027nm
            f19302(378), --193.025THz , 1553.1276nm
            f19301(379), --193.0125THz , 1553.2282nm
            f19298(380), --192.9875THz , 1553.4294nm
            f19297(381), --192.975THz , 1553.53nm
            f19296(382), --192.9625THz , 1553.6307nm
            f19293(383), --192.9375THz , 1553.832nm
            f19292(384), --192.925THz , 1553.9327nm
            f19291(385), --192.9125THz , 1554.0333nm
            f19288(386), --192.8875THz , 1554.2348nm
            f19287(387), --192.875THz , 1554.3355nm
            f19286(388), --192.8625THz , 1554.4362nm
            f19283(389), --192.8375THz , 1554.6378nm
            f19282(390), --192.825THz , 1554.7385nm
            f19281(391), --192.8125THz , 1554.8393nm
            f19278(392), --192.7875THz , 1555.041nm
            f19277(393), --192.775THz , 1555.1418nm
            f19276(394), --192.7625THz , 1555.2426nm
            f19273(395), --192.7375THz , 1555.4444nm
            f19272(396), --192.725THz , 1555.5452nm
            f19271(397), --192.7125THz , 1555.6461nm
            f19268(398), --192.6875THz , 1555.848nm
            f19267(399), --192.675THz , 1555.9489nm
            f19266(400), --192.6625THz , 1556.0499nm
            f19263(401), --192.6375THz , 1556.2518nm
            f19262(402), --192.625THz , 1556.3528nm
            f19261(403), --192.6125THz , 1556.4538nm
            f19258(404), --192.5875THz , 1556.6558nm
            f19257(405), --192.575THz , 1556.7569nm
            f19256(406), --192.5625THz , 1556.8579nm
            f19253(407), --192.5375THz , 1557.0601nm
            f19252(408), --192.525THz , 1557.1612nm
            f19251(409), --192.5125THz , 1557.2623nm
            f19248(410), --192.4875THz , 1557.4646nm
            f19247(411), --192.475THz , 1557.5657nm
            f19246(412), --192.4625THz , 1557.6669nm
            f19243(413), --192.4375THz , 1557.8692nm
            f19242(414), --192.425THz , 1557.9704nm
            f19241(415), --192.4125THz , 1558.0716nm
            f19238(416), --192.3875THz , 1558.2741nm
            f19237(417), --192.375THz , 1558.3754nm
            f19236(418), --192.3625THz , 1558.4766nm
            f19233(419), --192.3375THz , 1558.6792nm
            f19232(420), --192.325THz , 1558.7805nm
            f19231(421), --192.3125THz , 1558.8818nm
            f19228(422), --192.2875THz , 1559.0845nm
            f19227(423), --192.275THz , 1559.1858nm
            f19226(424), --192.2625THz , 1559.2872nm
            f19223(425), --192.2375THz , 1559.49nm
            f19222(426), --192.225THz , 1559.5914nm
            f19221(427), --192.2125THz , 1559.6928nm
            f19218(428), --192.1875THz , 1559.8957nm
            f19217(429), --192.175THz , 1559.9972nm
            f19216(430), --192.1625THz , 1560.0987nm
            f19213(431), --192.1375THz , 1560.3016nm
            f19212(432), --192.125THz , 1560.4032nm
            f19211(433), --192.1125THz , 1560.5047nm
            f19208(434), --192.0875THz , 1560.7078nm
            f19207(435), --192.075THz , 1560.8094nm
            f19206(436), --192.0625THz , 1560.9109nm
            f19203(437), --192.0375THz , 1561.1141nm
            f19202(438), --192.025THz , 1561.2158nm
            f19201(439), --192.0125THz , 1561.3174nm
            f19198(440), --191.9875THz , 1561.5207nm
            f19197(441), --191.975THz , 1561.6224nm
            f19196(442), --191.9625THz , 1561.7241nm
            f19195(443), --191.95THz , 1561.8258nm
            f19193(444), --191.9375THz , 1561.9275nm
            f19192(445), --191.925THz , 1562.0292nm
            f19191(446), --191.9125THz , 1562.131nm
            f19190(447), --191.9THz , 1562.2327nm
            f19188(448), --191.8875THz , 1562.3345nm
            f19187(449), --191.875THz , 1562.4363nm
            f19186(450), --191.8625THz , 1562.5381nm
            f19185(451), --191.85THz , 1562.6399nm
            f19183(452), --191.8375THz , 1562.7417nm
            f19182(453), --191.825THz , 1562.8435nm
            f19181(454), --191.8125THz , 1562.9454nm
            f19180(455), --191.8THz , 1563.0472nm
            f19178(456), --191.7875THz , 1563.1491nm
            f19177(457), --191.775THz , 1563.251nm
            f19176(458), --191.7625THz , 1563.3529nm
            f19175(459), --191.75THz , 1563.4548nm
            f19173(460), --191.7375THz , 1563.5567nm
            f19172(461), --191.725THz , 1563.6587nm
            f19171(462), --191.7125THz , 1563.7606nm
            f19170(463), --191.7THz , 1563.8626nm
            f19168(464), --191.6875THz , 1563.9646nm
            f19167(465), --191.675THz , 1564.0666nm
            f19166(466), --191.6625THz , 1564.1686nm
            f19165(467), --191.65THz , 1564.2706nm
            f19163(468), --191.6375THz , 1564.3726nm
            f19162(469), --191.625THz , 1564.4747nm
            f19161(470), --191.6125THz , 1564.5767nm
            f19160(471), --191.6THz , 1564.6788nm
            f19158(472), --191.5875THz , 1564.7809nm
            f19157(473), --191.575THz , 1564.883nm
            f19156(474), --191.5625THz , 1564.9851nm
            f19155(475), --191.55THz , 1565.0872nm
            f19153(476), --191.5375THz , 1565.1894nm
            f19152(477), --191.525THz , 1565.2915nm
            f19151(478), --191.5125THz , 1565.3937nm
            f19150(479), --191.5THz , 1565.4959nm
            f19148(480), --191.4875THz , 1565.5981nm
            f19147(481), --191.475THz , 1565.7003nm
            f19146(482), --191.4625THz , 1565.8025nm
            f19145(483), --191.45THz , 1565.9047nm
            f19143(484), --191.4375THz , 1566.007nm
            f19142(485), --191.425THz , 1566.1092nm
            f19141(486), --191.4125THz , 1566.2115nm
            f19140(487), --191.4THz , 1566.3138nm
            f19138(488), --191.3875THz , 1566.4161nm
            f19137(489), --191.375THz , 1566.5184nm
            f19136(490), --191.3625THz , 1566.6207nm
            f19135(491), --191.35THz , 1566.7231nm
            f19133(492), --191.3375THz , 1566.8254nm
            f19132(493), --191.325THz , 1566.9278nm
            f19131(494), --191.3125THz , 1567.0302nm
            f19130(495), --191.3THz , 1567.1326nm
            f19128(496), --191.2875THz , 1567.235nm
            f19127(497), --191.275THz , 1567.3374nm
            f19126(498), --191.2625THz , 1567.4398nm
            f19125(499), --191.25THz , 1567.5423nm
            notDefined(500),
            g1490(501), --1490,00nm
            f19123(502), --191.2375THz , 1567.6447nm
            f19122(503), --191.225THz , 1567.7472nm
            f19121(504), --191.2125THz , 1567.8497nm
            f19608(505), --196.08750THz , 1528.8708nm
            f19607(506), --196.0750THz , 1528.9683nm
            f19606(507), --196.06250THz , 1529.0658nm
            f19603(509), --196.03750THz , 1529.2608nm
            f19602(510), --196.02500THz , 1529.3583nm
            f19601(511), --196.01250THz , 1529.4558nm
            systemSelect(512),
            g850g900(513), --G850 & G900
            f19120(514) --191.20THz , 1567.9518nm
        }

FspR7ChannelIdentifierCaps ::= TEXTUAL-CONVENTION
  STATUS        current
  DESCRIPTION
        "Channel"
  SYNTAX    BITS
        {
            capUndefined(0),
            capD01(1),
            capD02(2),
            capD03(3),
            capD04(4),
            capD05(5),
            capD06(6),
            capD07(7),
            capD08(8),
            capD09(9),
            capD10(10),
            capD11(11),
            capD12(12),
            capD13(13),
            capD14(14),
            capD15(15),
            capD16(16),
            capD17(17),
            capD18(18),
            capD19(19),
            capD20(20),
            capD21(21),
            capD22(22),
            capD23(23),
            capD24(24),
            capD25(25),
            capD26(26),
            capD27(27),
            capD28(28),
            capD29(29),
            capD30(30),
            capD31(31),
            capD32(32),
            capD33(33),
            capD34(34),
            capD35(35),
            capD36(36),
            capD37(37),
            capD38(38),
            capD39(39),
            capD40(40),
            capD41(41),
            capD42(42),
            capD43(43),
            capD44(44),
            capD45(45),
            capD46(46),
            capD47(47),
            capD48(48),
            capD49(49),
            capD50(50),
            capD51(51),
            capD52(52),
            capD53(53),
            capD54(54),
            capD55(55),
            capD56(56),
            capD57(57),
            capD58(58),
            capD59(59),
            capD60(60),
            capD61(61),
            capD62(62),
            capD63(63),
            capD64(64),
            capDc1(65),
            capDc2(66),
            capDc3(67),
            capDc4(68),
            capDc5(69),
            capDc6(70),
            capDc7(71),
            capDc8(72),
            capDl1(73),
            capDl2(74),
            capDl3(75),
            capDl4(76),
            capDl5(77),
            capDl6(78),
            capDl7(79),
            capDl8(80),
            capDc9(81),
            capDl9(82),
            capF19640(83),
            capF19635(84),
            capF19630(85),
            capF19625(86),
            capF19620(87),
            capF19615(88),
            capF19605(89),
            capC1470(91),
            capC1490(92),
            capC1510(93),
            capC1530(94),
            capC1550(95),
            capC1570(96),
            capC1590(97),
            capC1610(98),
            capS1310(99),
            capS1630(100),
            capG850(101),
            capG1310(102),
            capG1550(103),
            -- capAny(104),
            capNotInGrid(105),
            capS1510(106),
            capF19610(107),
            capF19595(108),
            capF19585(109),
            capF19575(110),
            capF19565(111),
            capF19555(112),
            capF19545(113),
            capF19535(114),
            capF19525(115),
            capF19515(116),
            capF19505(117),
            capF19495(118),
            capF19485(119),
            capF19475(120),
            capF19465(121),
            capF19455(122),
            capF19445(123),
            capF19435(124),
            capF19425(125),
            capF19415(126),
            capF19405(127),
            capF19395(128),
            capF19385(129),
            capF19375(130),
            capF19365(131),
            capF19355(132),
            capF19345(133),
            capF19335(134),
            capF19325(135),
            capF19315(136),
            capF19305(137),
            capF19295(138),
            capF19285(139),
            capF19275(140),
            capF19265(141),
            capF19255(142),
            capF19245(143),
            capF19235(144),
            capF19225(145),
            capF19215(146),
            capF19205(147),
            capF19600(148),
            capF19590(149),
            capF19580(150),
            capF19570(151),
            capF19560(152),
            capF19550(153),
            capF19540(154),
            capF19530(155),
            capF19520(156),
            capF19510(157),
            capF19500(158),
            capF19490(159),
            capF19480(160),
            capF19470(161),
            capF19460(162),
            capF19450(163),
            capF19440(164),
            capF19430(165),
            capF19420(166),
            capF19410(167),
            capF19400(168),
            capF19390(169),
            capF19380(170),
            capF19370(171),
            capF19360(172),
            capF19350(173),
            capF19340(174),
            capF19330(175),
            capF19320(176),
            capF19310(177),
            capF19300(178),
            capF19290(179),
            capF19280(180),
            capF19270(181),
            capF19260(182),
            capF19250(183),
            capF19240(184),
            capF19230(185),
            capF19220(186),
            capF19210(187),
            capF19200(188),
            capC1270(189),
            capC1290(190),
            capC1310(191),
            capC1330(192),
            capC1350(193),
            capC1370(194),
            capC1430(195),
            capC1450(196),
            capS1610(197),
            capT1650(198),
            capS1490(199),
            capF19598(200),
            capF19597(201),
            capF19596(202),
            capF19593(203),
            capF19592(204),
            capF19591(205),
            capF19588(206),
            capF19587(207),
            capF19586(208),
            capF19583(209),
            capF19582(210),
            capF19581(211),
            capF19578(212),
            capF19577(213),
            capF19576(214),
            capF19573(215),
            capF19572(216),
            capF19571(217),
            capF19568(218),
            capF19567(219),
            capF19566(220),
            capF19563(221),
            capF19562(222),
            capF19561(223),
            capF19558(224),
            capF19557(225),
            capF19556(226),
            capF19553(227),
            capF19552(228),
            capF19551(229),
            capF19548(230),
            capF19547(231),
            capF19546(232),
            capF19543(233),
            capF19542(234),
            capF19541(235),
            capF19538(236),
            capF19537(237),
            capF19536(238),
            capF19533(239),
            capF19532(240),
            capF19531(241),
            capF19528(242),
            capF19527(243),
            capF19526(244),
            capF19523(245),
            capF19522(246),
            capF19521(247),
            capF19518(248),
            capF19517(249),
            capF19516(250),
            capF19513(251),
            capF19512(252),
            capF19511(253),
            capF19508(254),
            capF19507(255),
            capF19506(256),
            capF19503(257),
            capF19502(258),
            capF19501(259),
            capF19498(260),
            capF19497(261),
            capF19496(262),
            capF19493(263),
            capF19492(264),
            capF19491(265),
            capF19488(266),
            capF19487(267),
            capF19486(268),
            capF19483(269),
            capF19482(270),
            capF19481(271),
            capF19478(272),
            capF19477(273),
            capF19476(274),
            capF19473(275),
            capF19472(276),
            capF19471(277),
            capF19468(278),
            capF19467(279),
            capF19466(280),
            capF19463(281),
            capF19462(282),
            capF19461(283),
            capF19458(284),
            capF19457(285),
            capF19456(286),
            capF19453(287),
            capF19452(288),
            capF19451(289),
            capF19448(290),
            capF19447(291),
            capF19446(292),
            capF19443(293),
            capF19442(294),
            capF19441(295),
            capF19438(296),
            capF19437(297),
            capF19436(298),
            capF19433(299),
            capF19432(300),
            capF19431(301),
            capF19428(302),
            capF19427(303),
            capF19426(304),
            capF19423(305),
            capF19422(306),
            capF19421(307),
            capF19418(308),
            capF19417(309),
            capF19416(310),
            capF19413(311),
            capF19412(312),
            capF19411(313),
            capF19408(314),
            capF19407(315),
            capF19406(316),
            capF19403(317),
            capF19402(318),
            capF19401(319),
            capF19398(320),
            capF19397(321),
            capF19396(322),
            capF19393(323),
            capF19392(324),
            capF19391(325),
            capF19388(326),
            capF19387(327),
            capF19386(328),
            capF19383(329),
            capF19382(330),
            capF19381(331),
            capF19378(332),
            capF19377(333),
            capF19376(334),
            capF19373(335),
            capF19372(336),
            capF19371(337),
            capF19368(338),
            capF19367(339),
            capF19366(340),
            capF19363(341),
            capF19362(342),
            capF19361(343),
            capF19358(344),
            capF19357(345),
            capF19356(346),
            capF19353(347),
            capF19352(348),
            capF19351(349),
            capF19348(350),
            capF19347(351),
            capF19346(352),
            capF19343(353),
            capF19342(354),
            capF19341(355),
            capF19338(356),
            capF19337(357),
            capF19336(358),
            capF19333(359),
            capF19332(360),
            capF19331(361),
            capF19328(362),
            capF19327(363),
            capF19326(364),
            capF19323(365),
            capF19322(366),
            capF19321(367),
            capF19318(368),
            capF19317(369),
            capF19316(370),
            capF19313(371),
            capF19312(372),
            capF19311(373),
            capF19308(374),
            capF19307(375),
            capF19306(376),
            capF19303(377),
            capF19302(378),
            capF19301(379),
            capF19298(380),
            capF19297(381),
            capF19296(382),
            capF19293(383),
            capF19292(384),
            capF19291(385),
            capF19288(386),
            capF19287(387),
            capF19286(388),
            capF19283(389),
            capF19282(390),
            capF19281(391),
            capF19278(392),
            capF19277(393),
            capF19276(394),
            capF19273(395),
            capF19272(396),
            capF19271(397),
            capF19268(398),
            capF19267(399),
            capF19266(400),
            capF19263(401),
            capF19262(402),
            capF19261(403),
            capF19258(404),
            capF19257(405),
            capF19256(406),
            capF19253(407),
            capF19252(408),
            capF19251(409),
            capF19248(410),
            capF19247(411),
            capF19246(412),
            capF19243(413),
            capF19242(414),
            capF19241(415),
            capF19238(416),
            capF19237(417),
            capF19236(418),
            capF19233(419),
            capF19232(420),
            capF19231(421),
            capF19228(422),
            capF19227(423),
            capF19226(424),
            capF19223(425),
            capF19222(426),
            capF19221(427),
            capF19218(428),
            capF19217(429),
            capF19216(430),
            capF19213(431),
            capF19212(432),
            capF19211(433),
            capF19208(434),
            capF19207(435),
            capF19206(436),
            capF19203(437),
            capF19202(438),
            capF19201(439),
            capF19198(440),
            capF19197(441),
            capF19196(442),
            capF19195(443),
            capF19193(444),
            capF19192(445),
            capF19191(446),
            capF19190(447),
            capF19188(448),
            capF19187(449),
            capF19186(450),
            capF19185(451),
            capF19183(452),
            capF19182(453),
            capF19181(454),
            capF19180(455),
            capF19178(456),
            capF19177(457),
            capF19176(458),
            capF19175(459),
            capF19173(460),
            capF19172(461),
            capF19171(462),
            capF19170(463),
            capF19168(464),
            capF19167(465),
            capF19166(466),
            capF19165(467),
            capF19163(468),
            capF19162(469),
            capF19161(470),
            capF19160(471),
            capF19158(472),
            capF19157(473),
            capF19156(474),
            capF19155(475),
            capF19153(476),
            capF19152(477),
            capF19151(478),
            capF19150(479),
            capF19148(480),
            capF19147(481),
            capF19146(482),
            capF19145(483),
            capF19143(484),
            capF19142(485),
            capF19141(486),
            capF19140(487),
            capF19138(488),
            capF19137(489),
            capF19136(490),
            capF19135(491),
            capF19133(492),
            capF19132(493),
            capF19131(494),
            capF19130(495),
            capF19128(496),
            capF19127(497),
            capF19126(498),
            capF19125(499),
            capNotDefined(500),
            capG1490(501),
            capF19123(502),
            capF19122(503),
            capF19121(504),
            capF19608(505),
            capF19607(506),
            capF19606(507),
            capF19603(509),
            capF19602(510),
            capF19601(511),
            capSystemSelect(512),
            capG850g900(513),
            capF19120(514)
        }

FspR7ChannelNumber ::= TEXTUAL-CONVENTION
  STATUS        current
  DESCRIPTION
        "CWDM channels; DWDM frequencies (50 GHz grid according ITU-T"
  SYNTAX    INTEGER
        {
            undefined(0),
            f19600(1), --196,00THz 1529,55nm D01
            f19590(2), --195,90THz 1530,33nm D02
            f19580(3), --195,80THz 1531,12nm D03
            f19570(4), --195,70THz 1531,90nm D04
            f19550(5), --195,50THz 1533,47nm D05
            f19540(6), --195,40THz 1534,25nm D06
            f19530(7), --195,30THz 1535,04nm D07
            f19520(8), --195,20THz 1535,82nm D08
            f19500(9), --195,00THz 1537,40nm D09
            f19490(10), --194,90THz 1538,19nm D10
            f19480(11), --194,80THz 1538,98nm D11
            f19470(12), --194,70THz 1539,77nm D12
            f19450(13), --194,50THz 1541,35nm D13
            f19440(14), --194,40THz 1542,14nm D14
            f19430(15), --194,30THz 1542,94nm D15
            f19420(16), --194,20THz 1543,73nm D16
            f19380(17), --193,80THz 1546,92nm D17
            f19370(18), --193,70THz 1547,72nm D18
            f19360(19), --193,60THz 1548,51nm D19
            f19350(20), --193,50THz 1549,32nm D20
            f19330(21), --193,30THz 1550,92nm D21
            f19320(22), --193,20THz 1551,72nm D22
            f19310(23), --193,10THz 1552,52nm D23
            f19300(24), --193,00THz 1553,33nm D24
            f19280(25), --192,80THz 1554,94nm D25
            f19270(26), --192,70THz 1555,75nm D26
            f19260(27), --192,60THz 1556,55nm D27
            f19250(28), --192,50THz 1557,36nm D28
            f19230(29), --192,30THz 1558,98nm D29
            f19220(30), --192,20THz 1559,79nm D30
            f19210(31), --192,10THz 1560,61nm D31
            f19200(32), --192,00THz 1561,42nm D32
            f19100(33), --191,00THz 1569,59nm D33
            f19090(34), --190,90THz 1570,42nm D34
            f19080(35), --190,80THz 1571,24nm D35
            f19070(36), --190,70THz 1572,06nm D36
            f19050(37), --190,50THz 1573,71nm D37
            f19040(38), --190,40THz 1574,54nm D38
            f19030(39), --190,30THz 1575,37nm D39
            f19020(40), --190,20THz 1576,20nm D40
            f19000(41), --190,00THz 1577,86nm D41
            f18990(42), --189,90THz 1578,69nm D42
            f18980(43), --189,80THz 1579,52nm D43
            f18970(44), --189,70THz 1580,35nm D44
            f18950(45), --189,50THz 1582,02nm D45
            f18940(46), --189,40THz 1582,85nm D46
            f18930(47), --189,30THz 1583,69nm D47
            f18920(48), --189,20THz 1584,53nm D48
            f18880(49), --188,80THz 1587,88nm D49
            f18870(50), --188,70THz 1588,73nm D50
            f18860(51), --188,60THz 1589,57nm D51
            f18850(52), --188,50THz 1590,41nm D52
            f18830(53), --188,30THz 1592,10nm D53
            f18820(54), --188,20THz 1592,95nm D54
            f18810(55), --188,10THz 1593,79nm D55
            f18800(56), --188,00THz 1594,64nm D56
            f18780(57), --187,80THz 1596,34nm D57
            f18770(58), --187,70THz 1597,19nm D58
            f18760(59), --187,60THz 1598,04nm D59
            f18750(60), --187,50THz 1598,89nm D60
            f18730(61), --187,30THz 1600,60nm D61
            f18720(62), --187,20THz 1601,56nm D62
            f18710(63), --187,10THz 1602,31nm D63
            f18700(64), --187,00THz 1603,17nm D64
            f19560(65), --195,60THz 1532,68nm DC1
            f19510(66), --195,10THz 1536,61nm DC2
            f19460(67), --194,60THz 1540,56nm DC3
            f19410(68), --194,10THz 1544,53nm DC4
            f19390(69), --193,90THz 1546,12nm DC5
            f19340(70), --193,40THz 1550,12nm DC6
            f19290(71), --192,90THz 1554,13nm DC7
            f19240(72), --192,40THz 1558,17nm DC8
            f19060(73), --190,60THz 1572,89nm DL1
            f19010(74), --190,10THz 1577,03nm DL2
            f18960(75), --189,60THz 1581,18nm DL3
            f18910(76), --189,10THz 1585,36nm DL4
            f18890(77), --188,90THz 1587,04nm DL5
            f18840(78), --188,40THz 1591,26nm DL6
            f18790(79), --187,90THz 1595,49nm DL7
            f18740(80), --187,40THz 1599,75nm DL8
            f19400(81), --194,00THz 1545,322nm DC9
            f18900(82), --189,00THz 1586,203nm DL9
            f19640(83), --196.40THz 1526.44nm
            f19635(84), --196.35THz 1526.83nm
            f19630(85), --196.30THz 1527.22nm
            f19625(86), --196.25THz 1527.60nm
            f19620(87), --196.20THz 1527.99nm
            f19615(88), --196.15THz 1528.38nm
            f19605(89), --196.05THz 1529.16nm
            c1470(90), --1470,00nm
            c1490(91), --1490,00nm
            c1510(92), --1510,00nm
            c1530(93), --1530,00nm
            c1550(94), --1550,00nm
            c1570(95), --1570,00nm
            c1590(96), --1590,00nm
            c1610(97), --1610,00nm
            s1310(98), --1310,00nm
            s1630(99), --1630,00nm
            g850(100), --850,00nm
            g1310(101), --1310,00nm
            g1550(102), --1550,00nm
            null(103),
            nig(104),
            s1510(105), --1510,00nm
            f19610(106), --196,10THz  1528,7734nm
            f19595(107), --195,95THz  1529,9436nm
            f19585(108), --195,85THz  1530,7248nm
            f19575(109), --195,75THz  1531,5068nm
            f19565(110), --195,65THz  1532,2896nm
            f19555(111), --195,55THz  1533,0732nm
            f19545(112), --195,45THz  1533,8575nm
            f19535(113), --195,35THz  1534,6427nm
            f19525(114), --195,25THz  1535,4287nm
            f19515(115), --195,15THz  1536,2155nm
            f19505(116), --195,05THz  1537,0031nm
            f19495(117), --194,95THz  1537,7915nm
            f19485(118), --194,85THz  1538,5807nm
            f19475(119), --194,75THz  1539,3708nm
            f19465(120), --194,65THz  1540,1616nm
            f19455(121), --194,55THz  1540,9533nm
            f19445(122), --194,45THz  1541,7457nm
            f19435(123), --194,35THz  1542,5390nm
            f19425(124), --194,25THz  1543,3331nm
            f19415(125), --194,15THz  1544,1280nm
            f19405(126), --194,05THz  1544,9238nm
            f19395(127), --193,95THz  1545,7203nm
            f19385(128), --193,85THz  1546,5177nm
            f19375(129), --193,75THz  1547,3159nm
            f19365(130), --193,65THz  1548,1149nm
            f19355(131), --193,55THz  1548,9148nm
            f19345(132), --193,45THz  1549,7155nm
            f19335(133), --193,35THz  1550,5170nm
            f19325(134), --193,25THz  1551,3193nm
            f19315(135), --193,15THz  1552,1225nm
            f19305(136), --193,05THz  1552,9265nm
            f19295(137), --192,95THz  1553,7313nm
            f19285(138), --192,85THz  1554,5370nm
            f19275(139), --192,75THz  1555,3435nm
            f19265(140), --192,65THz  1556,1508nm
            f19255(141), --192,55THz  1556,9590nm
            f19245(142), --192,45THz  1557,7680nm
            f19235(143), --192,35THz  1558,5779nm
            f19225(144), --192,25THz  1559,3886nm
            f19215(145), --192,15THz  1560,2001nm
            f19205(146), --192,05THz  1561,0125nm
            f19195(147), --191.95THz 1561.83nm
            f19190(148), --191.90THz 1562.23nm
            f19185(149), --191.85THz 1562.64nm
            f19180(150), --191.80THz 1563.05nm
            f19175(151), --191.75THz 1563.45nm
            f19170(152), --191.70THz 1563.86nm
            f19165(153), --191.65THz 1564.27nm
            f19160(154), --191.60THz 1564.68nm
            f19155(155), --191.55THz 1565.09nm
            f19150(156), --191.50THz 1565.50nm
            f19145(157), --191.45THz 1565.90nm
            f19140(158), --191.40THz 1566.31nm
            f19135(159), --191.35THz 1566.72nm
            f19130(160), --191.30THz 1567.13nm
            f19125(161), --191.25THz 1567.54nm
            f19120(162), --191.20THz 1567.95nm
            f19115(163), --191.15THz 1568.36nm
            f19110(164), --191.10THz 1568.77nm
            f19105(165), --191.05THz 1569.18nm
            f19095(166), --190.95THz 1570.00nm
            f19085(167), --190.85THz 1570.83nm
            f19075(168), --190.75THz 1571.65nm
            f19065(169), --190.65THz 1572.48nm
            f19055(170), --190.55THz 1573.30nm
            f19045(171), --190.45THz 1574.13nm
            f19035(172), --190.35THz 1574.95nm
            f19025(173), --190.25THz 1575.78nm
            f19015(174), --190.15THz 1576.61nm
            f19005(175), --190.05THz 1577.44nm
            f18995(176), --189.95THz 1578.27nm
            f18985(177), --189.85THz 1579.10nm
            f18975(178), --189.75THz 1579.93nm
            f18965(179), --189.65THz 1580.77nm
            f18955(180), --189.55THz 1581.60nm
            f18945(181), --189.45THz 1582.44nm
            f18935(182), --189.35THz 1583.27nm
            f18925(183), --189.25THz 1584.11nm
            f18915(184), --189.15THz 1584.95nm
            f18905(185), --189.05THz 1585.78nm
            f18895(186), --188.95THz 1586.62nm
            f18885(187), --188.85THz 1587.46nm
            f18875(188), --188.75THz 1588.30nm
            f18865(189), --188.65THz 1589.15nm
            f18855(190), --188.55THz 1589.99nm
            f18845(191), --188.45THz 1590.83nm
            f18835(192), --188.35THz 1591.68nm
            f18825(193), --188.25THz 1592.52nm
            f18815(194), --188.15THz 1593.37nm
            f18805(195), --188.05THz 1594.22nm
            f18795(196), --187.95THz 1595.06nm
            f18785(197), --187.85THz 1595.91nm
            f18775(198), --187.75THz 1596.76nm
            f18765(199), --187.65THz 1597.61nm
            f18755(200), --187.55THz 1598.47nm
            f18745(201), --187.45THz 1599.32nm
            f18735(202), --187.35THz 1600.17nm
            f18725(203), --187.25THz 1601.03nm
            f18715(204), --187.15THz 1601.88nm
            f18705(205), --187.05THz 1602.74nm
            c1270(206), --1270,00nm
            c1290(207), --1290,00nm
            c1310(208), --1310,00nm
            c1330(209), --1330,00nm
            c1350(210), --1350,00nm
            c1370(211), --1370,00nm
            c1430(212), --1430,00nm
            c1450(213), --1450,00nm
            t1650(214), --1650,00nm OTDR
            s1490(215), --1490,00nm OSC
            s1610(216), --1610,00nm OSC
            f19598(217), --195.9875THz , 1529.6509nm
            f19597(218), --195.975THz , 1529.7485nm
            f19596(219), --195.9625THz , 1529.8461nm
            f19593(220), --195.9375THz , 1530.0413nm
            f19592(221), --195.925THz , 1530.1389nm
            f19591(222), --195.9125THz , 1530.2365nm
            f19588(223), --195.8875THz , 1530.4318nm
            f19587(224), --195.875THz , 1530.5295nm
            f19586(225), --195.8625THz , 1530.6271nm
            f19583(226), --195.8375THz , 1530.8225nm
            f19582(227), --195.825THz , 1530.9203nm
            f19581(228), --195.8125THz , 1531.018nm
            f19578(229), --195.7875THz , 1531.2135nm
            f19577(230), --195.775THz , 1531.3112nm
            f19576(231), --195.7625THz , 1531.409nm
            f19573(232), --195.7375THz , 1531.6046nm
            f19572(233), --195.725THz , 1531.7024nm
            f19571(234), --195.7125THz , 1531.8003nm
            f19568(235), --195.6875THz , 1531.996nm
            f19567(236), --195.675THz , 1532.0938nm
            f19566(237), --195.6625THz , 1532.1917nm
            f19563(238), --195.6375THz , 1532.3875nm
            f19562(239), --195.625THz , 1532.4854nm
            f19561(240), --195.6125THz , 1532.5833nm
            f19558(241), --195.5875THz , 1532.7792nm
            f19557(242), --195.575THz , 1532.8772nm
            f19556(243), --195.5625THz , 1532.9752nm
            f19553(244), --195.5375THz , 1533.1712nm
            f19552(245), --195.525THz , 1533.2692nm
            f19551(246), --195.5125THz , 1533.3672nm
            f19548(247), --195.4875THz , 1533.5633nm
            f19547(248), --195.475THz , 1533.6614nm
            f19546(249), --195.4625THz , 1533.7595nm
            f19543(250), --195.4375THz , 1533.9557nm
            f19542(251), --195.425THz , 1534.0538nm
            f19541(252), --195.4125THz , 1534.1519nm
            f19538(253), --195.3875THz , 1534.3482nm
            f19537(254), --195.375THz , 1534.4464nm
            f19536(255), --195.3625THz , 1534.5445nm
            f19533(256), --195.3375THz , 1534.7409nm
            f19532(257), --195.325THz , 1534.8392nm
            f19531(258), --195.3125THz , 1534.9374nm
            f19528(259), --195.2875THz , 1535.1339nm
            f19527(260), --195.275THz , 1535.2321nm
            f19526(261), --195.2625THz , 1535.3304nm
            f19523(262), --195.2375THz , 1535.527nm
            f19522(263), --195.225THz , 1535.6253nm
            f19521(264), --195.2125THz , 1535.7237nm
            f19518(265), --195.1875THz , 1535.9204nm
            f19517(266), --195.175THz , 1536.0187nm
            f19516(267), --195.1625THz , 1536.1171nm
            f19513(268), --195.1375THz , 1536.3139nm
            f19512(269), --195.125THz , 1536.4123nm
            f19511(270), --195.1125THz , 1536.5108nm
            f19508(271), --195.0875THz , 1536.7077nm
            f19507(272), --195.075THz , 1536.8061nm
            f19506(273), --195.0625THz , 1536.9046nm
            f19503(274), --195.0375THz , 1537.1016nm
            f19502(275), --195.025THz , 1537.2001nm
            f19501(276), --195.0125THz , 1537.2987nm
            f19498(277), --194.9875THz , 1537.4958nm
            f19497(278), --194.975THz , 1537.5943nm
            f19496(279), --194.9625THz , 1537.6929nm
            f19493(280), --194.9375THz , 1537.8901nm
            f19492(281), --194.925THz , 1537.9888nm
            f19491(282), --194.9125THz , 1538.0874nm
            f19488(283), --194.8875THz , 1538.2847nm
            f19487(284), --194.875THz , 1538.3834nm
            f19486(285), --194.8625THz , 1538.482nm
            f19483(286), --194.8375THz , 1538.6795nm
            f19482(287), --194.825THz , 1538.7782nm
            f19481(288), --194.8125THz , 1538.8769nm
            f19478(289), --194.7875THz , 1539.0744nm
            f19477(290), --194.775THz , 1539.1732nm
            f19476(291), --194.7625THz , 1539.272nm
            f19473(292), --194.7375THz , 1539.4696nm
            f19472(293), --194.725THz , 1539.5684nm
            f19471(294), --194.7125THz , 1539.6672nm
            f19468(295), --194.6875THz , 1539.865nm
            f19467(296), --194.675THz , 1539.9638nm
            f19466(297), --194.6625THz , 1540.0627nm
            f19463(298), --194.6375THz , 1540.2605nm
            f19462(299), --194.625THz , 1540.3595nm
            f19461(300), --194.6125THz , 1540.4584nm
            f19458(301), --194.5875THz , 1540.6563nm
            f19457(302), --194.575THz , 1540.7553nm
            f19456(303), --194.5625THz , 1540.8543nm
            f19453(304), --194.5375THz , 1541.0523nm
            f19452(305), --194.525THz , 1541.1513nm
            f19451(306), --194.5125THz , 1541.2503nm
            f19448(307), --194.4875THz , 1541.4485nm
            f19447(308), --194.475THz , 1541.5475nm
            f19446(309), --194.4625THz , 1541.6466nm
            f19443(310), --194.4375THz , 1541.8448nm
            f19442(311), --194.425THz , 1541.944nm
            f19441(312), --194.4125THz , 1542.0431nm
            f19438(313), --194.3875THz , 1542.2414nm
            f19437(314), --194.375THz , 1542.3406nm
            f19436(315), --194.3625THz , 1542.4398nm
            f19433(316), --194.3375THz , 1542.6382nm
            f19432(317), --194.325THz , 1542.7375nm
            f19431(318), --194.3125THz , 1542.8367nm
            f19428(319), --194.2875THz , 1543.0352nm
            f19427(320), --194.275THz , 1543.1345nm
            f19426(321), --194.2625THz , 1543.2338nm
            f19423(322), --194.2375THz , 1543.4324nm
            f19422(323), --194.225THz , 1543.5318nm
            f19421(324), --194.2125THz , 1543.6311nm
            f19418(325), --194.1875THz , 1543.8298nm
            f19417(326), --194.175THz , 1543.9292nm
            f19416(327), --194.1625THz , 1544.0286nm
            f19413(328), --194.1375THz , 1544.2275nm
            f19412(329), --194.125THz , 1544.3269nm
            f19411(330), --194.1125THz , 1544.4263nm
            f19408(331), --194.0875THz , 1544.6253nm
            f19407(332), --194.075THz , 1544.7248nm
            f19406(333), --194.0625THz , 1544.8243nm
            f19403(334), --194.0375THz , 1545.0233nm
            f19402(335), --194.025THz , 1545.1228nm
            f19401(336), --194.0125THz , 1545.2224nm
            f19398(337), --193.9875THz , 1545.4215nm
            f19397(338), --193.975THz , 1545.5211nm
            f19396(339), --193.9625THz , 1545.6207nm
            f19393(340), --193.9375THz , 1545.82nm
            f19392(341), --193.925THz , 1545.9196nm
            f19391(342), --193.9125THz , 1546.0193nm
            f19388(343), --193.8875THz , 1546.2186nm
            f19387(344), --193.875THz , 1546.3183nm
            f19386(345), --193.8625THz , 1546.418nm
            f19383(346), --193.8375THz , 1546.6174nm
            f19382(347), --193.825THz , 1546.7172nm
            f19381(348), --193.8125THz , 1546.8169nm
            f19378(349), --193.7875THz , 1547.0165nm
            f19377(350), --193.775THz , 1547.1163nm
            f19376(351), --193.7625THz , 1547.2161nm
            f19373(352), --193.7375THz , 1547.4157nm
            f19372(353), --193.725THz , 1547.5156nm
            f19371(354), --193.7125THz , 1547.6155nm
            f19368(355), --193.6875THz , 1547.8152nm
            f19367(356), --193.675THz , 1547.9151nm
            f19366(357), --193.6625THz , 1548.015nm
            f19363(358), --193.6375THz , 1548.2149nm
            f19362(359), --193.625THz , 1548.3148nm
            f19361(360), --193.6125THz , 1548.4148nm
            f19358(361), --193.5875THz , 1548.6148nm
            f19357(362), --193.575THz , 1548.7148nm
            f19356(363), --193.5625THz , 1548.8148nm
            f19353(364), --193.5375THz , 1549.0148nm
            f19352(365), --193.525THz , 1549.1149nm
            f19351(366), --193.5125THz , 1549.2149nm
            f19348(367), --193.4875THz , 1549.4151nm
            f19347(368), --193.475THz , 1549.5152nm
            f19346(369), --193.4625THz , 1549.6153nm
            f19343(370), --193.4375THz , 1549.8156nm
            f19342(371), --193.425THz , 1549.9158nm
            f19341(372), --193.4125THz , 1550.0159nm
            f19338(373), --193.3875THz , 1550.2163nm
            f19337(374), --193.375THz , 1550.3165nm
            f19336(375), --193.3625THz , 1550.4167nm
            f19333(376), --193.3375THz , 1550.6172nm
            f19332(377), --193.325THz , 1550.7175nm
            f19331(378), --193.3125THz , 1550.8178nm
            f19328(379), --193.2875THz , 1551.0183nm
            f19327(380), --193.275THz , 1551.1187nm
            f19326(381), --193.2625THz , 1551.219nm
            f19323(382), --193.2375THz , 1551.4197nm
            f19322(383), --193.225THz , 1551.52nm
            f19321(384), --193.2125THz , 1551.6204nm
            f19318(385), --193.1875THz , 1551.8212nm
            f19317(386), --193.175THz , 1551.9216nm
            f19316(387), --193.1625THz , 1552.022nm
            f19313(388), --193.1375THz , 1552.2229nm
            f19312(389), --193.125THz , 1552.3234nm
            f19311(390), --193.1125THz , 1552.4239nm
            f19308(391), --193.0875THz , 1552.6249nm
            f19307(392), --193.075THz , 1552.7254nm
            f19306(393), --193.0625THz , 1552.8259nm
            f19303(394), --193.0375THz , 1553.027nm
            f19302(395), --193.025THz , 1553.1276nm
            f19301(396), --193.0125THz , 1553.2282nm
            f19298(397), --192.9875THz , 1553.4294nm
            f19297(398), --192.975THz , 1553.53nm
            f19296(399), --192.9625THz , 1553.6307nm
            f19293(400), --192.9375THz , 1553.832nm
            f19292(401), --192.925THz , 1553.9327nm
            f19291(402), --192.9125THz , 1554.0333nm
            f19288(403), --192.8875THz , 1554.2348nm
            f19287(404), --192.875THz , 1554.3355nm
            f19286(405), --192.8625THz , 1554.4362nm
            f19283(406), --192.8375THz , 1554.6378nm
            f19282(407), --192.825THz , 1554.7385nm
            f19281(408), --192.8125THz , 1554.8393nm
            f19278(409), --192.7875THz , 1555.041nm
            f19277(410), --192.775THz , 1555.1418nm
            f19276(411), --192.7625THz , 1555.2426nm
            f19273(412), --192.7375THz , 1555.4444nm
            f19272(413), --192.725THz , 1555.5452nm
            f19271(414), --192.7125THz , 1555.6461nm
            f19268(415), --192.6875THz , 1555.848nm
            f19267(416), --192.675THz , 1555.9489nm
            f19266(417), --192.6625THz , 1556.0499nm
            f19263(418), --192.6375THz , 1556.2518nm
            f19262(419), --192.625THz , 1556.3528nm
            f19261(420), --192.6125THz , 1556.4538nm
            f19258(421), --192.5875THz , 1556.6558nm
            f19257(422), --192.575THz , 1556.7569nm
            f19256(423), --192.5625THz , 1556.8579nm
            f19253(424), --192.5375THz , 1557.0601nm
            f19252(425), --192.525THz , 1557.1612nm
            f19251(426), --192.5125THz , 1557.2623nm
            f19248(427), --192.4875THz , 1557.4646nm
            f19247(428), --192.475THz , 1557.5657nm
            f19246(429), --192.4625THz , 1557.6669nm
            f19243(430), --192.4375THz , 1557.8692nm
            f19242(431), --192.425THz , 1557.9704nm
            f19241(432), --192.4125THz , 1558.0716nm
            f19238(433), --192.3875THz , 1558.2741nm
            f19237(434), --192.375THz , 1558.3754nm
            f19236(435), --192.3625THz , 1558.4766nm
            f19233(436), --192.3375THz , 1558.6792nm
            f19232(437), --192.325THz , 1558.7805nm
            f19231(438), --192.3125THz , 1558.8818nm
            f19228(439), --192.2875THz , 1559.0845nm
            f19227(440), --192.275THz , 1559.1858nm
            f19226(441), --192.2625THz , 1559.2872nm
            f19223(442), --192.2375THz , 1559.49nm
            f19222(443), --192.225THz , 1559.5914nm
            f19221(444), --192.2125THz , 1559.6928nm
            f19218(445), --192.1875THz , 1559.8957nm
            f19217(446), --192.175THz , 1559.9972nm
            f19216(447), --192.1625THz , 1560.0987nm
            f19213(448), --192.1375THz , 1560.3016nm
            f19212(449), --192.125THz , 1560.4032nm
            f19211(450), --192.1125THz , 1560.5047nm
            f19208(451), --192.0875THz , 1560.7078nm
            f19207(452), --192.075THz , 1560.8094nm
            f19206(453), --192.0625THz , 1560.9109nm
            f19203(454), --192.0375THz , 1561.1141nm
            f19202(455), --192.025THz , 1561.2158nm
            f19201(456), --192.0125THz , 1561.3174nm
            f19198(457), --191.9875THz , 1561.5207nm
            f19197(458), --191.975THz , 1561.6224nm
            f19196(459), --191.9625THz , 1561.7241nm
            f19193(460), --191.9375THz , 1561.9275nm
            f19192(461), --191.925THz , 1562.0292nm
            f19191(462), --191.9125THz , 1562.131nm
            f19188(463), --191.8875THz , 1562.3345nm
            f19187(464), --191.875THz , 1562.4363nm
            f19186(465), --191.8625THz , 1562.5381nm
            f19183(466), --191.8375THz , 1562.7417nm
            f19182(467), --191.825THz , 1562.8435nm
            f19181(468), --191.8125THz , 1562.9454nm
            f19178(469), --191.7875THz , 1563.1491nm
            f19177(470), --191.775THz , 1563.251nm
            f19176(471), --191.7625THz , 1563.3529nm
            f19173(472), --191.7375THz , 1563.5567nm
            f19172(473), --191.725THz , 1563.6587nm
            f19171(474), --191.7125THz , 1563.7606nm
            f19168(475), --191.6875THz , 1563.9646nm
            f19167(476), --191.675THz , 1564.0666nm
            f19166(477), --191.6625THz , 1564.1686nm
            f19163(478), --191.6375THz , 1564.3726nm
            f19162(479), --191.625THz , 1564.4747nm
            f19161(480), --191.6125THz , 1564.5767nm
            f19158(481), --191.5875THz , 1564.7809nm
            f19157(482), --191.575THz , 1564.883nm
            f19156(483), --191.5625THz , 1564.9851nm
            f19153(484), --191.5375THz , 1565.1894nm
            f19152(485), --191.525THz , 1565.2915nm
            f19151(486), --191.5125THz , 1565.3937nm
            f19148(487), --191.4875THz , 1565.5981nm
            f19147(488), --191.475THz , 1565.7003nm
            f19146(489), --191.4625THz , 1565.8025nm
            f19143(490), --191.4375THz , 1566.007nm
            f19142(491), --191.425THz , 1566.1092nm
            f19141(492), --191.4125THz , 1566.2115nm
            f19138(493), --191.3875THz , 1566.4161nm
            f19137(494), --191.375THz , 1566.5184nm
            f19136(495), --191.3625THz , 1566.6207nm
            f19133(496), --191.3375THz , 1566.8254nm
            f19132(497), --191.325THz , 1566.9278nm
            f19131(498), --191.3125THz , 1567.0302nm
            f19128(499), --191.2875THz , 1567.235nm
            f19127(500), --191.275THz , 1567.3374nm
            f19126(501), --191.2625THz , 1567.4398nm
            g1490(502), --1490,00nm
            f19123(503), --191.2375THz , 1567.6447nm
            f19122(504), --191.225THz , 1567.7472nm
            f19121(505), --191.2125THz , 1567.8497nm
            f19608(506), --196.08750THz , 1528.8708nm
            f19607(507), --196.0750THz , 1528.9683nm
            f19606(508), --196.06250THz , 1529.0658nm
            f19603(509), --196.03750THz , 1529.2608nm
            f19602(510), --196.02500THz , 1529.3583nm
            f19601(511), --196.01250THz , 1529.4558nm
            g850g900(512) --850,00nm & 900,00nm
        }

FspR7ChannelNumberCaps ::= TEXTUAL-CONVENTION
  STATUS        current
  DESCRIPTION
        "CWDM channels; DWDM frequencies (50 GHz grid according ITU-T"
  SYNTAX    BITS
        {
            capUndefined(0),
            capF19600(1),
            capF19590(2),
            capF19580(3),
            capF19570(4),
            capF19550(5),
            capF19540(6),
            capF19530(7),
            capF19520(8),
            capF19500(9),
            capF19490(10),
            capF19480(11),
            capF19470(12),
            capF19450(13),
            capF19440(14),
            capF19430(15),
            capF19420(16),
            capF19380(17),
            capF19370(18),
            capF19360(19),
            capF19350(20),
            capF19330(21),
            capF19320(22),
            capF19310(23),
            capF19300(24),
            capF19280(25),
            capF19270(26),
            capF19260(27),
            capF19250(28),
            capF19230(29),
            capF19220(30),
            capF19210(31),
            capF19200(32),
            capF19100(33),
            capF19090(34),
            capF19080(35),
            capF19070(36),
            capF19050(37),
            capF19040(38),
            capF19030(39),
            capF19020(40),
            capF19000(41),
            capF18990(42),
            capF18980(43),
            capF18970(44),
            capF18950(45),
            capF18940(46),
            capF18930(47),
            capF18920(48),
            capF18880(49),
            capF18870(50),
            capF18860(51),
            capF18850(52),
            capF18830(53),
            capF18820(54),
            capF18810(55),
            capF18800(56),
            capF18780(57),
            capF18770(58),
            capF18760(59),
            capF18750(60),
            capF18730(61),
            capF18720(62),
            capF18710(63),
            capF18700(64),
            capF19560(65),
            capF19510(66),
            capF19460(67),
            capF19410(68),
            capF19390(69),
            capF19340(70),
            capF19290(71),
            capF19240(72),
            capF19060(73),
            capF19010(74),
            capF18960(75),
            capF18910(76),
            capF18890(77),
            capF18840(78),
            capF18790(79),
            capF18740(80),
            capF19400(81),
            capF18900(82),
            capF19640(83),
            capF19635(84),
            capF19630(85),
            capF19625(86),
            capF19620(87),
            capF19615(88),
            capF19605(89),
            capC1470(90),
            capC1490(91),
            capC1510(92),
            capC1530(93),
            capC1550(94),
            capC1570(95),
            capC1590(96),
            capC1610(97),
            capS1310(98),
            capS1630(99),
            capG850(100),
            capG1310(101),
            capG1550(102),
            capNull(103),
            capNig(104),
            capS1510(105),
            capF19610(106),
            capF19595(107),
            capF19585(108),
            capF19575(109),
            capF19565(110),
            capF19555(111),
            capF19545(112),
            capF19535(113),
            capF19525(114),
            capF19515(115),
            capF19505(116),
            capF19495(117),
            capF19485(118),
            capF19475(119),
            capF19465(120),
            capF19455(121),
            capF19445(122),
            capF19435(123),
            capF19425(124),
            capF19415(125),
            capF19405(126),
            capF19395(127),
            capF19385(128),
            capF19375(129),
            capF19365(130),
            capF19355(131),
            capF19345(132),
            capF19335(133),
            capF19325(134),
            capF19315(135),
            capF19305(136),
            capF19295(137),
            capF19285(138),
            capF19275(139),
            capF19265(140),
            capF19255(141),
            capF19245(142),
            capF19235(143),
            capF19225(144),
            capF19215(145),
            capF19205(146),
            capF19195(147),
            capF19190(148),
            capF19185(149),
            capF19180(150),
            capF19175(151),
            capF19170(152),
            capF19165(153),
            capF19160(154),
            capF19155(155),
            capF19150(156),
            capF19145(157),
            capF19140(158),
            capF19135(159),
            capF19130(160),
            capF19125(161),
            capF19120(162),
            capF19115(163),
            capF19110(164),
            capF19105(165),
            capF19095(166),
            capF19085(167),
            capF19075(168),
            capF19065(169),
            capF19055(170),
            capF19045(171),
            capF19035(172),
            capF19025(173),
            capF19015(174),
            capF19005(175),
            capF18995(176),
            capF18985(177),
            capF18975(178),
            capF18965(179),
            capF18955(180),
            capF18945(181),
            capF18935(182),
            capF18925(183),
            capF18915(184),
            capF18905(185),
            capF18895(186),
            capF18885(187),
            capF18875(188),
            capF18865(189),
            capF18855(190),
            capF18845(191),
            capF18835(192),
            capF18825(193),
            capF18815(194),
            capF18805(195),
            capF18795(196),
            capF18785(197),
            capF18775(198),
            capF18765(199),
            capF18755(200),
            capF18745(201),
            capF18735(202),
            capF18725(203),
            capF18715(204),
            capF18705(205),
            capC1270(206),
            capC1290(207),
            capC1310(208),
            capC1330(209),
            capC1350(210),
            capC1370(211),
            capC1430(212),
            capC1450(213),
            capT1650(214),
            capS1490(215),
            capS1610(216),
            capF19598(217),
            capF19597(218),
            capF19596(219),
            capF19593(220),
            capF19592(221),
            capF19591(222),
            capF19588(223),
            capF19587(224),
            capF19586(225),
            capF19583(226),
            capF19582(227),
            capF19581(228),
            capF19578(229),
            capF19577(230),
            capF19576(231),
            capF19573(232),
            capF19572(233),
            capF19571(234),
            capF19568(235),
            capF19567(236),
            capF19566(237),
            capF19563(238),
            capF19562(239),
            capF19561(240),
            capF19558(241),
            capF19557(242),
            capF19556(243),
            capF19553(244),
            capF19552(245),
            capF19551(246),
            capF19548(247),
            capF19547(248),
            capF19546(249),
            capF19543(250),
            capF19542(251),
            capF19541(252),
            capF19538(253),
            capF19537(254),
            capF19536(255),
            capF19533(256),
            capF19532(257),
            capF19531(258),
            capF19528(259),
            capF19527(260),
            capF19526(261),
            capF19523(262),
            capF19522(263),
            capF19521(264),
            capF19518(265),
            capF19517(266),
            capF19516(267),
            capF19513(268),
            capF19512(269),
            capF19511(270),
            capF19508(271),
            capF19507(272),
            capF19506(273),
            capF19503(274),
            capF19502(275),
            capF19501(276),
            capF19498(277),
            capF19497(278),
            capF19496(279),
            capF19493(280),
            capF19492(281),
            capF19491(282),
            capF19488(283),
            capF19487(284),
            capF19486(285),
            capF19483(286),
            capF19482(287),
            capF19481(288),
            capF19478(289),
            capF19477(290),
            capF19476(291),
            capF19473(292),
            capF19472(293),
            capF19471(294),
            capF19468(295),
            capF19467(296),
            capF19466(297),
            capF19463(298),
            capF19462(299),
            capF19461(300),
            capF19458(301),
            capF19457(302),
            capF19456(303),
            capF19453(304),
            capF19452(305),
            capF19451(306),
            capF19448(307),
            capF19447(308),
            capF19446(309),
            capF19443(310),
            capF19442(311),
            capF19441(312),
            capF19438(313),
            capF19437(314),
            capF19436(315),
            capF19433(316),
            capF19432(317),
            capF19431(318),
            capF19428(319),
            capF19427(320),
            capF19426(321),
            capF19423(322),
            capF19422(323),
            capF19421(324),
            capF19418(325),
            capF19417(326),
            capF19416(327),
            capF19413(328),
            capF19412(329),
            capF19411(330),
            capF19408(331),
            capF19407(332),
            capF19406(333),
            capF19403(334),
            capF19402(335),
            capF19401(336),
            capF19398(337),
            capF19397(338),
            capF19396(339),
            capF19393(340),
            capF19392(341),
            capF19391(342),
            capF19388(343),
            capF19387(344),
            capF19386(345),
            capF19383(346),
            capF19382(347),
            capF19381(348),
            capF19378(349),
            capF19377(350),
            capF19376(351),
            capF19373(352),
            capF19372(353),
            capF19371(354),
            capF19368(355),
            capF19367(356),
            capF19366(357),
            capF19363(358),
            capF19362(359),
            capF19361(360),
            capF19358(361),
            capF19357(362),
            capF19356(363),
            capF19353(364),
            capF19352(365),
            capF19351(366),
            capF19348(367),
            capF19347(368),
            capF19346(369),
            capF19343(370),
            capF19342(371),
            capF19341(372),
            capF19338(373),
            capF19337(374),
            capF19336(375),
            capF19333(376),
            capF19332(377),
            capF19331(378),
            capF19328(379),
            capF19327(380),
            capF19326(381),
            capF19323(382),
            capF19322(383),
            capF19321(384),
            capF19318(385),
            capF19317(386),
            capF19316(387),
            capF19313(388),
            capF19312(389),
            capF19311(390),
            capF19308(391),
            capF19307(392),
            capF19306(393),
            capF19303(394),
            capF19302(395),
            capF19301(396),
            capF19298(397),
            capF19297(398),
            capF19296(399),
            capF19293(400),
            capF19292(401),
            capF19291(402),
            capF19288(403),
            capF19287(404),
            capF19286(405),
            capF19283(406),
            capF19282(407),
            capF19281(408),
            capF19278(409),
            capF19277(410),
            capF19276(411),
            capF19273(412),
            capF19272(413),
            capF19271(414),
            capF19268(415),
            capF19267(416),
            capF19266(417),
            capF19263(418),
            capF19262(419),
            capF19261(420),
            capF19258(421),
            capF19257(422),
            capF19256(423),
            capF19253(424),
            capF19252(425),
            capF19251(426),
            capF19248(427),
            capF19247(428),
            capF19246(429),
            capF19243(430),
            capF19242(431),
            capF19241(432),
            capF19238(433),
            capF19237(434),
            capF19236(435),
            capF19233(436),
            capF19232(437),
            capF19231(438),
            capF19228(439),
            capF19227(440),
            capF19226(441),
            capF19223(442),
            capF19222(443),
            capF19221(444),
            capF19218(445),
            capF19217(446),
            capF19216(447),
            capF19213(448),
            capF19212(449),
            capF19211(450),
            capF19208(451),
            capF19207(452),
            capF19206(453),
            capF19203(454),
            capF19202(455),
            capF19201(456),
            capF19198(457),
            capF19197(458),
            capF19196(459),
            capF19193(460),
            capF19192(461),
            capF19191(462),
            capF19188(463),
            capF19187(464),
            capF19186(465),
            capF19183(466),
            capF19182(467),
            capF19181(468),
            capF19178(469),
            capF19177(470),
            capF19176(471),
            capF19173(472),
            capF19172(473),
            capF19171(474),
            capF19168(475),
            capF19167(476),
            capF19166(477),
            capF19163(478),
            capF19162(479),
            capF19161(480),
            capF19158(481),
            capF19157(482),
            capF19156(483),
            capF19153(484),
            capF19152(485),
            capF19151(486),
            capF19148(487),
            capF19147(488),
            capF19146(489),
            capF19143(490),
            capF19142(491),
            capF19141(492),
            capF19138(493),
            capF19137(494),
            capF19136(495),
            capF19133(496),
            capF19132(497),
            capF19131(498),
            capF19128(499),
            capF19127(500),
            capF19126(501),
            capG1490(502),
            capF19123(503),
            capF19122(504),
            capF19121(505),
            capF19608(506),
            capF19607(507),
            capF19606(508),
            capF19603(509),
            capF19602(510),
            capF19601(511),
            capG850g900(512)
        }

FspR7ChannelRangeInventory ::= TEXTUAL-CONVENTION
  STATUS        current
  DESCRIPTION
        "Channel Range"
  SYNTAX    INTEGER
        {
            undefined(0),
            f19600f19122(1), --When BAND=C_CI, CHANNELS=192
            f19600f19125(2), --When BAND=C, CHANNELS=96
            f19597f19122(3), --When BAND=CI, Channels=96
            f19595f19200(4), --When BAND=C_CI, Channels=80
            f19590f19200(5), --When BAND=C, Channels=40
            f19595f19205(6), --When BAND=CI, Channels=40
            f19590f19500(7), --When BAND=C, Channels=10
            f19350f19260(8), --When BAND=C, Channels=10
            f19600f19123(9), --When BAND=C, CHANNELS=128
            f19610f19122(10), --When BAND=C, CHANNELS=391
            f19610f19123(11), --When BAND=C, CHANNELS=390
            f19600f19125F(12), --When BAND=C, CHANNELS=381
            f19600f19130(13), --When BAND=C, CHANNELS=48, CHA__SPC (Channel Spacing)=100GHz
            f19600f19200(14), --When BAND=C, CHANNELS=16, CHA__SPC (Channel Spacing)=100GHz.  Used by 16CSM/P-1HU#19600-19200-SFA/B
            f19600f19127(15), --When BAND=C, CHANNELS=64, CHA__SPC (Channel Spacing)=75GHz
            f19600f19520(16), --G.metro plug 9 channel 100GHz spacing
            f19520f19440(17), --G.metro plug 9 channel 100GHz spacing
            f19440f19360(18), --G.metro plug 9 channel 100GHz spacing
            f19360f19280(19), --G.metro plug 9 channel 100GHz spacing
            f19280f19200(20), --G.metro plug 9 channel 100GHz spacing
            f19200f19120(21), --G.metro plug 9 channel 100GHz spacing
            f196006250f191253125(22), --When BAND=C, Flex, XFP-AMP
            f19600f19125A(23), --When BAND=C, CHANNELS=127 to support ADVA CFP
            f19610f19125(24), --When BAND=C, CHANNELS=389 to support ADVA CFP
            f19200f19130(25), --G.metro plug 8 channel 100GHz spacing
            f19600f19127A(26) --When BAND=C, CHANNELS=127 to support ADVA CFP
        }

FspR7ChannelRangeInventoryCaps ::= TEXTUAL-CONVENTION
  STATUS        current
  DESCRIPTION
        "Channel Range"
  SYNTAX    BITS
        {
            capUndefined(0),
            capF19600f19122(1),
            capF19600f19125(2),
            capF19597f19122(3),
            capF19595f19200(4),
            capF19590f19200(5),
            capF19595f19205(6),
            capF19590f19500(7),
            capF19350f19260(8),
            capF19600f19123(9),
            capF19610f19122(10),
            capF19610f19123(11),
            capF19600f19125F(12),
            capF19600f19130(13),
            capF19600f19200(14),
            capF19600f19127(15),
            capF19600f19520(16),
            capF19520f19440(17),
            capF19440f19360(18),
            capF19360f19280(19),
            capF19280f19200(20),
            capF19200f19120(21),
            capF196006250f191253125(22),
            capF19600f19125A(23),
            capF19610f19125(24),
            capF19200f19130(25),
            capF19600f19127A(26)
        }

FspR7ChannelSpacing ::= TEXTUAL-CONVENTION
  STATUS        current
  DESCRIPTION
        "ITU Grid channel spacing"
  SYNTAX    INTEGER
        {
            undefined(0),
            spacing50Ghz(1),
            spacing100Ghz(2),
            spacing200Ghz(3),
            spacing25GHz(4),
            spacingFlex(5),
            spacing37GHz5(6),
            spacingHwDefined(7),
            spacing75GHz(8)
        }

FspR7ChannelSpacingCaps ::= TEXTUAL-CONVENTION
  STATUS        current
  DESCRIPTION
        "ITU Grid channel spacing"
  SYNTAX    BITS
        {
            capUndefined(0),
            capSpacing50Ghz(1),
            capSpacing100Ghz(2),
            capSpacing200Ghz(3),
            capSpacing25GHz(4),
            capSpacingFlex(5),
            capSpacing37GHz5(6),
            capSpacingHwDefined(7),
            capSpacing75GHz(8)
        }

FspR7ClientPortMode ::= TEXTUAL-CONVENTION
  STATUS        current
  DESCRIPTION
        "Client Port Mode"
  SYNTAX    INTEGER
        {
            undefined(0),
            reflectRemoteLed(1),
            monitorAndAlarm(2)
        }

FspR7ClientPortModeCaps ::= TEXTUAL-CONVENTION
  STATUS        current
  DESCRIPTION
        "Client Port Mode"
  SYNTAX    BITS
        {
            capUndefined(0),
            capReflectRemoteLed(1),
            capMonitorAndAlarm(2)
        }

FspR7ClientReplacementSignal ::= TEXTUAL-CONVENTION
  STATUS        current
  DESCRIPTION
        "Signal inserted/removed to/from payload when client signal is lost"
  SYNTAX    INTEGER
        {
            undefined(0),
            localFault(1),
            gais(2) --GAIS is PN11 AIS
        }

FspR7ClientReplacementSignalCaps ::= TEXTUAL-CONVENTION
  STATUS        current
  DESCRIPTION
        "Signal inserted/removed to/from payload when client signal is lost"
  SYNTAX    BITS
        {
            capUndefined(0),
            capLocalFault(1),
            capGais(2)
        }

FspR7CodeGain ::= TEXTUAL-CONVENTION
  STATUS        current
  DESCRIPTION
        "Forward Error Correction Coding gain"
  SYNTAX    INTEGER
        {
            undefined(0),
            high(1),
            mean(2),
            low(3)
        }

FspR7CodeGainCaps ::= TEXTUAL-CONVENTION
  STATUS        current
  DESCRIPTION
        "Forward Error Correction Coding gain"
  SYNTAX    BITS
        {
            capUndefined(0),
            capHigh(1),
            capMean(2),
            capLow(3)
        }

FspR7ColumnMark ::= TEXTUAL-CONVENTION
  STATUS        current
  DESCRIPTION
        "Enables Artificial Entities in chosen tables"
  SYNTAX    INTEGER
        {
            undefined(0),
            false(1),
            true(2)
        }

FspR7Command ::= TEXTUAL-CONVENTION
  STATUS        current
  DESCRIPTION
        ""
  SYNTAX        INTEGER
                {
                  undefined(0),
                  scheduleBackupScu(1),
                  scheduleBackupRemote(2),
                  copyNone(11),
                  download(12),
                  upload(13),
                  downloadScu(14),
                  uploadScu(15),
                  uploadPa(16),
                  downloadCf(17),
                  uploadCf(18),
                  eqptNone(31),
                  eqptInstall(32),
                  eqptReboot(33),
                  eqptActivate(34),
                  eqptUpdate(35),
                  eqptInstallFromStby(36),
                  eqptForceInstall(37),
                  ncuNone(51),
                  ncuDbBackup(52),
                  ncuDbRestor(53),
                  ncuInstall(54),
                  ncuRestart(55),
                  ncuActivate(56),
                  ncuImportAp(57),
                  ncuExportAp(58),
                  ncuActivateAp(59),
                  ncuActivateFdAp(60),
                  ncuAutoDownAndInstall(61),
                  ncuAutoInstall(62),
                  ncuDbBackupScu(63),
                  ncuFwSave(64),
                  ncuCryptoFwDownAndSave(65),
                  ncuCopyProfileRdisk(66),
                  ncuCopyProfilePdisk(67),
                  ncuCreateProfile(68),
                  ncuExportRef(69),
                  ncuSwitch(70),
                  ncuInstallCf(71),
                  ncuAutoInstallCf(72),
                  ncuActivateWithFw(73),
                  ncuGenSdp(74),
                  ncuGenSdpAndUpload(75),
                  ncuAlmDbBackup(76),
                  ncuAlmDbRestore(77),
                  ncuAlmActivate(78),
                  ncuStbFwSave(79),
                  ncuStbNativeFwDownAndSave(80),
                  ncuTestFwpAutoDownloadSettings(83),
                  ncuHdSysActFwDownAndSave(87),
                  ncuHdSysStbFwDownAndSave(88),
                  ncuImportMp(91),
                  ncuExportMp(92),
                  ncuActivateMp(93),
                  ncuDeactivateMp(94),
                  ncuCreateMp(95),
                  ncuDestroyMp(96),
                  ncuImportAndActivateMp(97),
                  ncuImportTp(98),
                  ncuExportTp(99),
                  ncuActivateTp(100),
                  ncuActivateFdTp(101),
                  ncuNativeFwDownAndSave(102)
                }

FspR7CommandState ::= TEXTUAL-CONVENTION
  STATUS        current
  DESCRIPTION
        ""
  SYNTAX        INTEGER
                {
                  undefined(0),
                  swActIdle(1),
                  swActFail(2),
                  swActInProgress(3),
                  dbActIdle(11),
                  dbActFail(12),
                  dbActInProgress(13),
                  apActIdle(21),
                  apActFail(22),
                  apActInProgress(23),
                  swInstallIdle(31),
                  swInstallTransferCon(32),
                  swInstallCon(33),
                  swInstallTransferPgm(34),
                  swInstallPgm(35),
                  swInstallTransferFwp(36),
                  swInstallFwp(37),
                  swInstallTransferSw(38),
                  swInstallSw(39),
                  swInstallTransferFwpe(40),
                  bootComplete(51),
                  bootInProgress(52),
                  bootFail(53),
                  bootRejected(54),
                  bootFwInstalling(55),
                  bootFwFail(56),
                  bootFwComplete(57),
                  bootFwActInProgress(58),
                  bootFwActFail(59),
                  bootFwActRejected(60),
                  bootFwActComplete(61),
                  bootFwDownloading(62),
                  bootFwDwnlFail(63),
                  bootFwDwnlComplete(64),
                  copyFileIdle(71),
                  copyFileChecksumFail(72),
                  copyFileAccessDenied(73),
                  copyFileFileNotExist(74),
                  copyFileConnectionFail(75),
                  copyFileProtocolFail(76),
                  copyFileNotEnoughSpace(77),
                  copyFileLoginFail(78),
                  copyFileTransferStart(79),
                  copyFileTransferInProgress(80),
                  copyFileTransferComplete(81),
                  copyFileSshHostKeyFail(82),
                  copyFileNoHostKeyFail(83),
                  copyFileProtocolDisabled(84),
                  copyFileNoSshKeyFail(85),
                  localCopyIdle(101),
                  localCopyFail(102),
                  localCopyStart(103),
                  localCopyComplete(104),
                  localCopyDenied(105),
                  localCopyCrcFail(106),
                  localCopyInstallMismatch(107),
                  localCopyIncorrectState(108),
                  localCopyInvalidFile(109),
                  localCopyFileSystemError(110),
                  localCopyFileNotExist(111),
                  localCopyBackupFail(112),
                  localCopyProfileLimitFail(113),
                  localCopyProfileDissallowed(114),
                  localCopyProfileExistFail(115),
                  localCopyWrongSecret(116),
                  localCopyWrongSignature(117)
                }

FspR7CommandBusy ::= TEXTUAL-CONVENTION
  STATUS        current
  DESCRIPTION
        "UBR Busy state"
  SYNTAX    INTEGER
        {
            undefined(0),
            idle(1),
            ubr(2),
            cserver(3)
        }

FspR7Conn ::= TEXTUAL-CONVENTION
  STATUS        current
  DESCRIPTION
        "Bidirectional | Unidirectional"
  SYNTAX    INTEGER
        {
            undefined(0),
            bi(1),
            uni(2)
        }

FspR7ConnCaps ::= TEXTUAL-CONVENTION
  STATUS        current
  DESCRIPTION
        "Bidirectional | Unidirectional"
  SYNTAX    BITS
        {
            capUndefined(0),
            capBi(1),
            capUni(2)
        }

FspR7ConnectorType ::= TEXTUAL-CONVENTION
  STATUS        current
  DESCRIPTION
        "Connector Type"
  SYNTAX    INTEGER
        {
            undefined(0),
            lc(1),
            rj45(2),
            mupc(3),
            dsub8(4),
            usbS(5),
            dsub44hd(6),
            fcApc(7),
            mpo(8), --MPO is the industry acronym for "Multi-Fiber Push On". A MPO Connector type is a Multi-fiber Connector, which is used for high density fiber interconnections.
            mbnc(9), --Micro-BNC
            hdBnc(10), --HD-BNC
            din(11), --DIN 1.0/2.3
            sc(12),
            fc(13),
            dsub26hd(14),
            unknown(15)
        }

FspR7ConnectorTypeCaps ::= TEXTUAL-CONVENTION
  STATUS        current
  DESCRIPTION
        "Connector Type"
  SYNTAX    BITS
        {
            capUndefined(0),
            capLc(1),
            capRj45(2),
            capMupc(3),
            capDsub8(4),
            capUsbS(5),
            capDsub44hd(6),
            capFcApc(7),
            capMpo(8),
            capMbnc(9),
            capHdBnc(10),
            capDin(11),
            capSc(12),
            capFc(13),
            capDsub26hd(14),
            capUnknown(15)
        }

FspR7ConnectState ::= TEXTUAL-CONVENTION
  STATUS        current
  DESCRIPTION
        "Connection State"
  SYNTAX    INTEGER
        {
            undefined(0),
            idle(1),
            idleReceive(2),
            idleTransmit(3),
            busy(4)
        }

FspR7CpAuthType ::= TEXTUAL-CONVENTION
  STATUS        current
  DESCRIPTION
        "OSPF Authentication Type"
  SYNTAX    INTEGER
        {
            undefined(0),
            none(1),
            simple(2),
            md5(3)
        }

FspR7CpAuthTypeCaps ::= TEXTUAL-CONVENTION
  STATUS        current
  DESCRIPTION
        "OSPF Authentication Type"
  SYNTAX    BITS
        {
            capUndefined(0),
            capNone(1),
            capSimple(2),
            capMd5(3)
        }

FspR7CrlMode ::= TEXTUAL-CONVENTION
  STATUS        current
  DESCRIPTION
        "Mechanism to be used for verifying certificate revocation (CRL)"
  SYNTAX    INTEGER
        {
            undefined(0),
            none(1), --Do not use any revocation mechanism.
            baseCrl(2), --Automatically update and process base CRL only - end-entity certificates only.
            deltaCrl(3), --Automatically update and process combined base and delta CRL. NOT SUPPORTED AS YET.
            oscp(4), --NOT SUPPORTED AS YET.
            baseCrlAll(5), --Automatically update and process base CRL only - issuing and end-entity certificates.
            deltaCrlAll(6) --Automatically update and process combined base and delta CRL. NOT SUPPORTED AS YET.
        }

FspR7CrlUpdateInterval ::= TEXTUAL-CONVENTION
  STATUS        current
  DESCRIPTION
        "Interval for automatic update of revocation CRL data."
  SYNTAX    INTEGER
        {
            undefined(0),
            none(1), --Update interval is irrelevant, because of CRL update mode being either manual or disabled altogether.
            manual(2), --Interval is undefined, i.e. update is triggered only manually.
            auto(3), --Determined automatically, based on current CRL data field(s) and extension(s), e.g. Next Upate.
            update5min(105), --Meant for development only. DEPRECATED
            update15min(1015),
            update30min(1030),
            update45min(1045),
            update1hour(2001),
            update3hours(2003),
            update6hours(2006),
            update12hours(2012),
            update24hours(2024),
            update1days(3001),
            update2days(3002),
            update5days(3005),
            update7days(3007)
        }

FspR7Date ::= TEXTUAL-CONVENTION
  DISPLAY-HINT        "2d-1d-1d"
  STATUS        current
  DESCRIPTION
        "A date specification.
        field  octets  contents                  range
        -----  ------  --------                  -----
        1      1-2   year*                     0..65536
        2       3    month                     1..12
        3       4    day                       1..31
        * Notes:             - the value of year is in network-byte order
        For example, Tuesday May 26, 1992 would be
        displayed as:
        1992-5-26"
  SYNTAX    OCTET STRING (SIZE(4..4))

FspR7DbActOperation ::= TEXTUAL-CONVENTION
  STATUS        current
  DESCRIPTION
        "Operation to work on F8 DB maintenance mode for shelf"
  SYNTAX    INTEGER
        {
            undefined(0),
            rls(1),
            accept(2),
            restore(3),
            rtf(4)
        }

FspR7DCFiberType ::= TEXTUAL-CONVENTION
  STATUS        current
  DESCRIPTION
        "Dispersion Compensation Fibertype"
  SYNTAX    INTEGER
        {
            undefined(0),
            singleMode(1), --Standard Single Mode Fiber
            trueWaveRs(2) --Truewave RS fiber
        }

FspR7DCFiberTypeCaps ::= TEXTUAL-CONVENTION
  STATUS        current
  DESCRIPTION
        "Dispersion Compensation Fibertype"
  SYNTAX    BITS
        {
            capUndefined(0),
            capSingleMode(1),
            capTrueWaveRs(2)
        }

FspR7DeploymentScenario ::= TEXTUAL-CONVENTION
  STATUS        current
  DESCRIPTION
        "Describes how the card is applied related to a network scenario"
  SYNTAX    INTEGER
        {
            undefined(0),
            generic(1), --NO additonal deployment information supplied [thus Protected as above OR Protected in a Channel Card Protection (not yet known) OR Unprotected OR possibly (unknown to this card) deployed in a VSM Protection scenario]
            backToBack(2), --IF MODE NOT = TRANSHST NOR MUXHST NOR REGEN back to back regenerator on pass-thru
            clientProt(3), --IF MODE NOT = TRANSHST OR MUXHST deployed in client layer protection and thus NOT used for HST Channel protection NOR Channel Card protection NOR VSM Protection
            passThrough(4), --IF MODE NOT = TRANSHST OR MUXHST deployed in client layer protection and thus NOT used for HST Channel protection NOR Channel Card protection NOR VSM Protection
            none(5) --Deployment not relevant
        }

FspR7DeploymentScenarioCaps ::= TEXTUAL-CONVENTION
  STATUS        current
  DESCRIPTION
        "Describes how the card is applied related to a network scenario"
  SYNTAX    BITS
        {
            capUndefined(0),
            capGeneric(1),
            capBackToBack(2),
            capClientProt(3),
            capPassThrough(4),
            capNone(5)
        }

FspR7DhcpServer ::= TEXTUAL-CONVENTION
  STATUS        current
  DESCRIPTION
        "Determines DHCP Server/Client mode of the NCU"
  SYNTAX    INTEGER
        {
            undefined(0),
            gne(1), --DHCP server runs on GNE; In case of OSC Ring
            local(2), --DHCP server runs on the NE locally; DHCP__STARTADDR and DHCP__STOPADDR are ignored; The server provides one IP address derived from the local interface IP address
            client(3), --Node is DHCP client, uses IP address obtained from DHCP server
            off(4), --DHCP Server/Client suppport is not used
            relay(5), --Node is a DHCP relay agent
            relayClient(6), --Node is a DHCP relay agent and a client
            clientLite(7) --Node is DHCP client - multiple selection available
        }

FspR7DhcpServerCaps ::= TEXTUAL-CONVENTION
  STATUS        current
  DESCRIPTION
        "Determines DHCP Server/Client mode of the NCU"
  SYNTAX    BITS
        {
            capUndefined(0),
            capGne(1),
            capLocal(2),
            capClient(3),
            capOff(4),
            capRelay(5),
            capRelayClient(6),
            capClientLite(7)
        }

FspR7Dhcpv6Server ::= TEXTUAL-CONVENTION
  STATUS        current
  DESCRIPTION
        "Determines DHCPV6 Server/Client mode of the NCU"
  SYNTAX    INTEGER
        {
            undefined(0),
            client(1), --Node is DHCP client, uses IP address obtained from DHCP server
            off(2), --DHCP Server/Client suppport is not used
            relay(3), --Node is a DHCP relay agent
            relayClient(4), --Node is a DHCP relay agent and a client
            clientLite(5) --Node is DHCP client - multiple selection available
        }

FspR7Dhcpv6ServerCaps ::= TEXTUAL-CONVENTION
  STATUS        current
  DESCRIPTION
        "Determines DHCPV6 Server/Client mode of the NCU"
  SYNTAX    BITS
        {
            capUndefined(0),
            capClient(1),
            capOff(2),
            capRelay(3),
            capRelayClient(4),
            capClientLite(5)
        }

FspR7DisableEnable ::= TEXTUAL-CONVENTION
  STATUS        current
  DESCRIPTION
        "Disable/Enable variable."
  SYNTAX    INTEGER
        {
            undefined(0),
            disable(1),
            enable(2)
        }

FspR7DisableEnableCaps ::= TEXTUAL-CONVENTION
  STATUS        current
  DESCRIPTION
        "Disable/Enable variable."
  SYNTAX    BITS
        {
            capUndefined(0),
            capDisable(1),
            capEnable(2)
        }

FspR7DispersionCompensation ::= TEXTUAL-CONVENTION
  STATUS        current
  DESCRIPTION
        "Dispersion Compensation Value in km of SSMF fiber"
  SYNTAX    INTEGER
        {
            undefined(0),
            dispertion10(1), --Dispersion value in km of transmission fiber
            dispertion20(2), --Dispersion value in km of transmission fiber
            dispertion40(3), --Dispersion value in km of transmission fiber
            dispertion60(4), --Dispersion value in km of transmission fiber
            dispertion80(5), --Dispersion value in km of transmission fiber
            dispertion100(6), --Dispersion value in km of transmission fiber
            dispertion30(7), --Dispersion value in km of transmission fiber
            dispertion50(8), --Dispersion value in km of transmission fiber
            dispertion70(9), --Dispersion value in km of transmission fiber
            dispertion90(10), --Dispersion value in km of transmission fiber
            dispertion160(11), --Dispersion value in km of transmission fiber
            dispertion240(12), --Dispersion value in km of transmission fiber
            dispertion320(13) --Dispersion value in km of transmission fiber
        }

FspR7DispersionCompensationCaps ::= TEXTUAL-CONVENTION
  STATUS        current
  DESCRIPTION
        "Dispersion Compensation Value in km of SSMF fiber"
  SYNTAX    BITS
        {
            capUndefined(0),
            capDispertion10(1),
            capDispertion20(2),
            capDispertion40(3),
            capDispertion60(4),
            capDispertion80(5),
            capDispertion100(6),
            capDispertion30(7),
            capDispertion50(8),
            capDispertion70(9),
            capDispertion90(10),
            capDispertion160(11),
            capDispertion240(12),
            capDispertion320(13)
        }

FspR7DispersionModes ::= TEXTUAL-CONVENTION
  STATUS        current
  DESCRIPTION
        "Chromatic Dispersion Compensation Mode"
  SYNTAX    INTEGER
        {
            undefined(0),
            auto(1),
            man(2),
            fiberSwitch(3)
        }

FspR7DispersionModesCaps ::= TEXTUAL-CONVENTION
  STATUS        current
  DESCRIPTION
        "Chromatic Dispersion Compensation Mode"
  SYNTAX    BITS
        {
            capUndefined(0),
            capAuto(1),
            capMan(2),
            capFiberSwitch(3)
        }

FspR7DmLayer ::= TEXTUAL-CONVENTION
  STATUS        current
  DESCRIPTION
        "Data layer where the Delay Measurement was performed"
  SYNTAX    INTEGER
        {
            undefined(0),
            none(1),
            odu(2),
            tcma(3),
            tcmb(4),
            tcmc(5)
        }

FspR7DmsrmtOperation ::= TEXTUAL-CONVENTION
  STATUS        current
  DESCRIPTION
        "Delay Measurement start"
  SYNTAX    INTEGER
        {
            undefined(0),
            idle(1),
            odu(2),
            tcma(3),
            tcmb(4),
            tcmc(5)
        }

FspR7DmsrmtOperationCaps ::= TEXTUAL-CONVENTION
  STATUS        current
  DESCRIPTION
        "Delay Measurement start"
  SYNTAX    BITS
        {
            capUndefined(0),
            capIdle(1),
            capOdu(2),
            capTcma(3),
            capTcmb(4),
            capTcmc(5)
        }

FspR7DmsrmtStatus ::= TEXTUAL-CONVENTION
  STATUS        current
  DESCRIPTION
        "Status of the Delay Measurement"
  SYNTAX    INTEGER
        {
            undefined(0),
            notAvailable(1),
            ready(2),
            inProgress(3),
            complete(4),
            failed(5)
        }

FspR7EdfaOutputPowerRating ::= TEXTUAL-CONVENTION
  STATUS        current
  DESCRIPTION
        "Optical Output Power Rating - Inventory"
  SYNTAX    INTEGER
        {
            undefined(0),
            pwrOut10(1),
            pwrOut17(2),
            pwrOut18(3),
            pwrOut20(4),
            pwrOut15(5),
            pwrOut27(6),
            pwrOut26(7),
            pwrOut20UN10NU(8)
        }

FspR7EdfaOutputPowerRatingCaps ::= TEXTUAL-CONVENTION
  STATUS        current
  DESCRIPTION
        "Optical Output Power Rating - Inventory"
  SYNTAX    BITS
        {
            capUndefined(0),
            capPwrOut10(1),
            capPwrOut17(2),
            capPwrOut18(3),
            capPwrOut20(4),
            capPwrOut15(5),
            capPwrOut27(6),
            capPwrOut26(7),
            capPwrOut20UN10NU(8)
        }

FspR7EnableDisable ::= TEXTUAL-CONVENTION
  STATUS        current
  DESCRIPTION
        "Enable/Disable variable."
  SYNTAX    INTEGER
        {
            undefined(0),
            enable(1),
            disable(2)
        }

FspR7EnableDisableCaps ::= TEXTUAL-CONVENTION
  STATUS        current
  DESCRIPTION
        "Enable/Disable variable."
  SYNTAX    BITS
        {
            capUndefined(0),
            capEnable(1),
            capDisable(2)
        }

FspR7EncapsulationMethod ::= TEXTUAL-CONVENTION
  STATUS        current
  DESCRIPTION
        "Indicates the encapsulation method being used."
  SYNTAX    INTEGER
        {
            undefined(0),
            none(1),
            tttgmp(2),
            gmp(3),
            gfpT(4),
            gfpF(5)
        }

FspR7EntitySecondaryStates ::= TEXTUAL-CONVENTION
  STATUS        current
  DESCRIPTION
        "Variable for representing the secondary states of an entity."
  SYNTAX    BITS
        {
            ueq(0),
            meaState(1),
            sgeo(2),
            lpbkState(3),
            lkdo(4),
            frcdState(5),
            faf(6),
            flt(7),
            act(8),
            stbyh(9),
            psi(10),
            pri(11),
            dgn(12),
            busy(13),
            idleState(14),
            receiveIdleState(15),
            transmitIdleState(16),
            sgeoSrv(17),
            farEndPlugOutage(18),
            aseTableBuildState(19),
            testState(20),
            testFailed(21),
            stby(22),
            stbyInh(23),
            noBackup(24),
            degrade(25),
            swdl(26),
            kexIncomplete(27),
            noComm(28)
        }

FspR7EntityType ::= TEXTUAL-CONVENTION
  STATUS        current
  DESCRIPTION
        ""
  SYNTAX        INTEGER
                {
                  undefined(0),
                  eqpSh1hu(1),
                  eqpSh1huDc(2),
                  eqpSh3hu(3),
                  eqpSh7hu(4),
                  eqpF2kSh5hu(5),
                  eqpF2kSh6hu(6),
                  eqpDcm(7),
                  eqpSh9hu(8),
                  eqpUnknown(19),
                  eqpNcu(20),
                  eqpNcutif(21),
                  eqpScu(22),
                  eqpScue(23),
                  eqpR6cu(24),
                  eqpPsu1huac(25),
                  eqpPsu7huac(26),
                  eqpPsu7hudc(27),
                  eqpFcu7hu(28),
                  eqp2clsmd(29),
                  eqp2absmc(30),
                  eqp2bsmd(31),
                  eqp1Gsmud(32),
                  eqp4gsmd(33),
                  eqp8gsmd(34),
                  eqp1csmuc(35),
                  eqp1csmuewc(36),
                  eqp4csmd(37),
                  eqp4csmud(38),
                  eqp4csmc(39),
                  eqpOsfm(40),
                  eqp1pm(41),
                  eqp2pm(42),
                  eqp40csmd(43),
                  eqpDcf(44),
                  eqpEdfas(45),
                  eqpEdfasgc(46),
                  eqpEdfadgc(47),
                  eqpRaman(48),
                  eqp4tcc2g5(49),
                  eqp4tcc2g5d(50),
                  eqp4tcc10gd(51),
                  eqp4tcc10gc(52),
                  eqpWcc10gd(53),
                  eqpWcc10gc(54),
                  eqpWcc2g71N(55),
                  eqpWcc2g7d(56),
                  eqp2tcm2g5(57),
                  eqp2tca2g5(58),
                  eqp8tca10gd(59),
                  eqp8tca10gc(60),
                  eqpWca10gd(61),
                  eqpWca10gc(62),
                  eqp4tca4gd(63),
                  eqp4tca4gc(64),
                  eqpwca2g5(65),
                  eqp4tca1g3d(66),
                  eqp4tca1g3c(67),
                  eqp8tce2g5d(68),
                  eqp8tce2g5c(69),
                  eqpWcelsd(70),
                  eqpWcelsc(71),
                  eqpVsm(72),
                  eqpRsmolm(73),
                  eqpRsmsf(74),
                  eqpOscm(75),
                  eqp2oscm(76),
                  eqpDrm(77),
                  eqpXfpG(78),
                  eqpsfpd(79),
                  eqpSfpc(80),
                  eqpSfpg(81),
                  eqpSfpe(82),
                  eqpSh1hudcm(83),
                  eqpCustomc(84),
                  eqpCustomd(85),
                  eqpPsu1hudc(86),
                  eqpWcc2g7c(87),
                  eqp1csmuEwD(88),
                  eqp1csmuG(89),
                  eqp3BsmC(90),
                  eqp2Tca2g5s(91),
                  eqp8Csmuc(92),
                  eqpEdfaDgcb(93),
                  eqpOscmPn(94),
                  eqp4Tcc10gtd(95),
                  eqp4Tca4g(96),
                  eqpDcg(97),
                  eqp2Tcm2g5d(98),
                  eqp2Tcm2g5c(99),
                  eqpWcm2g5d(100),
                  eqpWcm2g5c(101),
                  eqpEdfmSgc(102),
                  eqpF2kDemiV2(103),
                  eqpPsm(104),
                  eqpNcu2e(105),
                  eqp8TceGl2g5d(106),
                  eqp8TceGl2g5c(107),
                  eqpDcf1hu(108),
                  eqp10tcc10gtd(109),
                  eqp10tcc10gd(110),
                  eqp10tcc10gc(111),
                  eqp16csmSfd(112),
                  eqpOsfmSf(113),
                  eqp2clsmSfd(114),
                  eqp3bsmEwc(115),
                  eqpEdfaSgcb(116),
                  eqpEdfaDgcv(117),
                  eqpWcc10gtd(118),
                  eqp2csmuEwc(119),
                  eqpEroadmDc(120),
                  eqpScuS(122),
                  eqp4opcm(123),
                  eqpUtm(124),
                  eqpPscu(125),
                  eqp40Csm2hu(126),
                  eqp2Twcc2g7(127),
                  eqp2Wca10g(130),
                  eqpNcuHp(131),
                  eqpNcu20085hu(132),
                  eqp20Pca10G(133),
                  eqpXfpC(137),
                  eqpXfpD(138),
                  eqpWcc40gtd(140),
                  eqpIlm(141),
                  eqpNcuII(142),
                  eqpCem9hu(143),
                  eqp8roadmC40(148),
                  eqp4Tcc40gtd(149),
                  eqp2pca10g(150),
                  eqp10pca10g(151),
                  eqp1csmuD(152),
                  eqpSfpOsC(153),
                  eqpSfpOdC(154),
                  eqpSfpOsG(155),
                  eqpSfpOdG(156),
                  eqpRoadmC80(157),
                  eqpccm8(158),
                  eqpPsu9hudc(159),
                  eqp4tca4gus(160),
                  eqp40Csm3huD(161),
                  eqp5psm(162),
                  eqpFan9hu(163),
                  eqp5tce10gtd(164),
                  eqp10tccs10gtd(165),
                  eqp40Csm3hudcD(166),
                  eqp40Csm3hudcDi(167),
                  eqp5gsmD(169),
                  eqp8csmD(170),
                  eqp2otfm(171),
                  eqp8otdr3hu(172),
                  eqpXfptD(173),
                  eqp40Csm3huDi(174),
                  eqp8CcmC80(175),
                  eqpEdfaD27(176),
                  eqp2Wcc10g(177),
                  eqp8RoadmC80(178),
                  eqp2Wcc10gAes(180),
                  eqp5tce10gtaesd(182),
                  eqpSh1hupf(183),
                  eqpFan1hu(185),
                  eqp10tcc10g(186),
                  eqpXfpOtnD(187),
                  eqpNcu2p(188),
                  eqpPsu9huac(190),
                  eqp2Raman(192),
                  eqpEdfaS26(193),
                  eqp5tces10gtd(194),
                  eqpScuII(195),
                  eqp11RoadmC96(196),
                  eqp8AdmC96(197),
                  eqp8CxmC96(198),
                  eqp8Shm(199),
                  eqpAmpShgcv(200),
                  eqpAmpSlgcv(201),
                  eqp2RamanC15(202),
                  eqpWcc100gtD(203),
                  eqpCfp4g(204),
                  eqpCfp10g(205),
                  eqpXfpTlnD(213),
                  eqp5tces10gtaesd(214),
                  eqp10tce100g(215),
                  eqp96Csm4HuD(216),
                  eqp4CfptD(217),
                  eqp2psm(218),
                  eqpWce100G(219),
                  eqp10Wxc10g(220),
                  eqpShx9hu(221),
                  eqpFanXhu(222),
                  eqp10tcc100gtbD(223),
                  eqp9RoadmC96(224),
                  eqp4Wce16g(225),
                  eqpSfpBG(226),
                  eqpSfpCdrG(227),
                  eqp10tce100gGf(228),
                  eqpSfpCdrC(229),
                  eqp5tce10gaes(234),
                  eqp5tce10g(235),
                  eqp5tces10gaes(236),
                  eqp5tces10g(237),
                  eqp4roadmC96(239),
                  eqpWcc100gtbD(240),
                  eqpEdfaS20(241),
                  eqp10tccSdi10g(242),
                  eqp4roadmEC96(243),
                  eqpSfptD(245),
                  eqpSfp2TxG(246),
                  eqpSfp2RxG(247),
                  eqpSfp2Txe(248),
                  eqpSfp2Rxe(249),
                  eqp2EdfaS20S10(250),
                  eqp10Tce100Gb(251),
                  eqp10Tce100gAes(252),
                  eqpSfpCdrD(253),
                  eqpSh1huDcEtemp(254),
                  eqp8psm(255),
                  eqp9ccmC96(256),
                  eqpWce100GB(257),
                  eqp16tcc10G(258),
                  eqp4Wcc10g(259),
                  eqp5wca16G(260),
                  eqpCfptCd(261),
                  eqpWccPcn100g(264),
                  eqpOppm(267),
                  eqp4cfpd(268),
                  eqpNcuS(269),
                  eqp10csmuD(270),
                  eqpUtmS(272),
                  eqpSfpBC(273),
                  eqp10Tce100gAesBsi(274),
                  eqpWccPcn100gAes(280),
                  eqpSfpRxTxG(282),
                  eqpSfpTlnD(283),
                  eqpCfpTfCd(284),
                  eqpXfpBG(285),
                  eqpFd128D(286),
                  eqpSfpBCdrG(289),
                  eqpMroadmC96(290),
                  eqpPsm40Mroadm(291),
                  eqpOsfma(292),
                  eqp10tcc100g(293),
                  eqpCfpTgCd(294),
                  eqpPsm80Mroadm(295),
                  eqp10Tce100gbAes(297),
                  eqpL3CmSina(298),
                  eqp9Tce10gAesG(300),
                  eqp9Tce10gAes(301),
                  eqp9Tce10g(302),
                  eqp9RoadmRs(303),
                  eqp16psm4(304),
                  eqp96Csm2HuD(305),
                  eqp9Tce10gAesF(307),
                  eqp10Tce100gAesF(308),
                  eqpMtpOscC(309),
                  eqpWcc100gAesF(311),
                  eqpCfpTrCd(312),
                  eqpWcc100gAesB(314),
                  eqpMapOscC(317),
                  eqpMtpbOscC(318),
                  eqpMapbOscC(319),
                  eqpWccPcn100gB(320),
                  eqp4psmS(321),
                  eqpWcc100gAesG(323),
                  eqpHdScm(324),
                  eqp48Csm1HuD(325),
                  eqpNcu3(326),
                  eqp2Twcc2g7b(327),
                  eqp8psm8(328),
                  eqp16psm8(329),
                  eqp32psm1hu(330),
                  eqpCfpTlCd(331),
                  eqp4Tcc100gAesG(332),
                  eqp4Tcc100gAes(333),
                  eqp81Csmu1650(334),
                  eqpMalpbOscC(335),
                  eqpSfpGmD(337),
                  eqpMalpOscC(338),
                  eqpCfpTaCd(339),
                  eqpSfpGmCdrD(340),
                  eqpSh1hupfEtemp(341),
                  eqpPsu1huFDc(342),
                  eqpFcu1huF(344),
                  eqpPsu1huFAc(345),
                  eqp8csmuD(346),
                  eqp6wca28G(348),
                  eqp8psmA(349),
                  eqpSfpAdtran(350),
                  eqpXfpAdtran(351),
                  eqp9csmuD(352),
                  eqpSfptAD(358),
                  eqpCfp2tBCd(379),
                  eqpPsmdc5(386),
                  eqpSh4R3(387),
                  eqpPs1x2Cr(395),
                  eqpScm6(396),
                  eqpSfpNotApproved(397),
                  eqpSfD19dctA(399),
                  eqpTScm(401),
                  eqpTMpM8DCt(402),
                  eqpTMp2D8DCt(403),
                  eqpEcm6(407),
                  eqpCem6(408),
                  eqpQSfp8g(409),
                  eqpQSfp1g(410),
                  eqpOF2D16DCT(411),
                  eqpCfp2tCb(430),
                  eqpTMp2D8Ct(431),
                  eqpFd64W(432),
                  eqpQSfp2bg(435),
                  eqpTMp2D3Dt(436),
                  eqpTMp2D12Ct(437),
                  eqpTFtm(438),
                  eqpTEcm(439),
                  eqpTCem2(441),
                  eqpTPsmac(442),
                  eqpTSh1R2(444),
                  eqpSh3(445),
                  eqpFtm7(446),
                  eqpPsmdc7(447),
                  eqpPsmac7(448),
                  eqpCem7(449),
                  eqpCfp2tgCd(450),
                  eqpMaB2C3LtA(453),
                  eqpMaB5Lt(454),
                  eqpCfp2tCd(455),
                  eqpMp2B4CtS(456),
                  eqpPsmdc3(457),
                  eqpQSfpNotApproved(458),
                  eqpQSfp10g(459),
                  eqpMa2C2C3LtA(461),
                  eqpQSfpDacCr(462),
                  eqpCem3(463),
                  eqpFtm3(464),
                  eqpPsmac3(465),
                  eqpSh1R(466),
                  eqpEcm3(467),
                  eqp4QsfpG(468),
                  eqpScm2(472),
                  eqpMa2C5Lt(473),
                  eqpPsmac6(474),
                  eqpQSfpDac(475),
                  eqpQSfpAoc(476),
                  eqpPsmdc4(478),
                  eqpPsmac5(479),
                  eqpFtm4(480),
                  eqpFtm2(481),
                  eqpPsmac4(482),
                  eqpPsmdc(483),
                  eqpCem2(485),
                  eqpCem4(486),
                  eqpEcm2(487),
                  eqpQSfp4g(488),
                  eqpMp2B4Ct(489),
                  eqpSh12(490),
                  eqpSh4R(491),
                  eqpTPsmdc(492),
                  eqpMp2B4CtCg(493),
                  eqp16csm1huSf(494),
                  eqp8csmuDP(495),
                  eqp8csmDP(496),
                  eqpSh1huP(497),
                  eqpPtp(499),
                  ifTypeOtu1(501),
                  ifTypeOtu2(502),
                  ifType10GbE(503),
                  ifTypeOc192(504),
                  ifTypeOc48(505),
                  ifTypeStm16(506),
                  ifTypeStm64(507),
                  ifType10GFC(508),
                  ifTypeF1062(510),
                  ifTypeF1250(511),
                  ifTypeFC(512),
                  ifTypeF125(513),
                  ifTypeF200(514),
                  ifTypeF9953(515),
                  ifTypeF10312(516),
                  ifTypeF10518(517),
                  ifTypeF2488(518),
                  ifTypeGfpF(519),
                  ifTypeGfpT(520),
                  ifTypeDccL(521),
                  ifTypeDccS(522),
                  ifTypeDccP(523),
                  ifTypeOdu1(524),
                  ifTypeGcc0(525),
                  ifTypeGcc1(526),
                  ifTypeGcc2(527),
                  ifTypeoch(528),
                  ifTypeOm(529),
                  ifTypeOt(534),
                  ifTypeE10or100bt(536),
                  ifTypeE100fx(537),
                  ifTypeCl(538),
                  ifType2GFC(539),
                  ifType2GCL(540),
                  ifType1GbE(541),
                  ifTypeEoc(542),
                  ifTypeSwitch(543),
                  ifTypePassive(544),
                  ifTypeF2500(545),
                  ifTypeSc(546),
                  ifTypeUch(547),
                  ifTypeF155(548),
                  ifTypeF622(549),
                  ifTypeF2125(550),
                  ifTypeF2666(551),
                  ifTypeF4250(552),
                  ifTypeF10709(554),
                  ifTypeF11095(555),
                  ifTypeF11318(556),
                  ifTypeLs(557),
                  ifType4GFC(558),
                  ifTypeGcc0S(559),
                  ifType2R(560),
                  ifTypePppIp(561),
                  ifTypeLanIp(562),
                  ifTypeSerial(564),
                  ifTypeModem(565),
                  ifTypeAdapt(566),
                  ifTypeAdaptd(567),
                  ifTypeGBEFR(569),
                  ifTypeVc4(570),
                  ifTypeVc3(571),
                  ifTypeSts1(572),
                  ifTypeEdfa(573),
                  ifTypeEdfaMid(574),
                  ifType10Gdw(575),
                  ifTypeOtu2Lan(576),
                  ifTypeOtu1Lan(577),
                  ifTypeOtu1Fc(578),
                  ifTypeOtu1Fc2G(579),
                  ifTypeF197(580),
                  ifTypeTif(581),
                  ifTypeSts3c(582),
                  ifTypeVs1(583),
                  ifType1GbETH(584),
                  ifTypeStm1(585),
                  ifTypeStm4(586),
                  ifTypeOc3(587),
                  ifTypeOc12(588),
                  ifTypeOtu1Stm1(589),
                  ifTypeOtu1Stm4(590),
                  ifTypeF166(591),
                  ifTypeF666(592),
                  ifTypeI2C(593),
                  ifTypeLifIP(594),
                  ifTypeSts24c(595),
                  ifTypeSts48c(596),
                  ifTypeLifte(597),
                  ifTypeRaman(598),
                  ifTypeIpWhiteList(599),
                  ifTypeOspfIp(600),
                  ifTypeEncapIp(601),
                  ifTypeOtu3(602),
                  ifTypeStm256(603),
                  ifTypeOc768(604),
                  ifTypeF10664(605),
                  ifTypeOdu2(606),
                  ifTypeF39813(607),
                  ifTypeVc4c8(608),
                  ifTypeVc4c16(609),
                  ifTypeF8500(610),
                  ifTypePb(611),
                  ifTypePolicer(612),
                  ifTypeQueue(613),
                  ifTypeFlowPoint(614),
                  ifTypeLag(615),
                  ifTypeElinePPP(616),
                  ifTypeEtree(617),
                  ifTypeEline(618),
                  ifTypeElan(619),
                  ifTypeCtrans(620),
                  ifTypeVs0(621),
                  ifTypeTug(622),
                  ifTypeMd(623),
                  ifTypeMa(624),
                  ifTypeDownMep(625),
                  ifTypeFMep(626),
                  ifType8GFC(627),
                  ifType10Gib(628),
                  ifTypeF10000(629),
                  ifTypeOtu2pFC8(630),
                  ifTypeOtu2pIB(631),
                  ifTypeOtu2pFC(632),
                  ifTypeOtu2pLAN(633),
                  ifTypeOtu2p(634),
                  ifTypeUpMep(635),
                  ifTypeOtdrCh(636),
                  ifTypeMaNet(637),
                  ifTypeMaComp(638),
                  ifTypeBridge(639),
                  ifType1000BaseT(640),
                  ifTypeOtu2E(641),
                  ifTypeOtu1E(642),
                  ifTypeOtu2F(643),
                  ifTypeF11049(644),
                  ifTypeLifteNum(645),
                  ifTypeLifteUnn(646),
                  ifTypeLifPbNum(647),
                  ifTypeLifSubUnn(648),
                  ifType5Gib(649),
                  ifTypeF5000(650),
                  ifTypeOtu2eEth(651),
                  ifTypeOdu0(652),
                  ifTypeFcu(653),
                  ifTypeOtu4(654),
                  ifType100GbE(660),
                  ifTypeOptical(661),
                  ifType10GbEWan(662),
                  ifType10GbELan(663),
                  ifTypeOduFlx(664),
                  ifTypeOtlc(665),
                  ifTypeOtu2ps(667),
                  ifTypeOdu2E(668),
                  ifTypeOdu1E(669),
                  ifTypeOdu2Lan(670),
                  ifTypeOdu4(671),
                  ifTypeLifVTeNum(673),
                  ifTypeLifVTeUnn(674),
                  ifTypeF14025(678),
                  ifTypeF270(681),
                  ifTypeF1485(684),
                  ifTypeF2970(685),
                  ifTypeF1483(688),
                  ifTypeF2967(689),
                  ifType40GbE(692),
                  ifTypeOdu3(693),
                  ifTypeF41250(694),
                  ifTypeF103125(695),
                  ifType16GFC(696),
                  ifTypeF1228(699),
                  ifTypeF2457(700),
                  ifTypeF3072(701),
                  ifTypeF4915(702),
                  ifTypeF6144(703),
                  ifTypeF9830(704),
                  ifTypeF10137(705),
                  ifTypeAdapt1485(707),
                  ifTypeAdapt2970(708),
                  ifTypeOtuC2PA(709),
                  ifTypeOtuC3PA(710),
                  ifTypeOtuC1P5A(711),
                  ifTypeE10to1000t(712),
                  ifTypeLldp(713),
                  ifType25GbE(714),
                  ifType32GFC(715),
                  ifTypeHdPppIp(720),
                  ifTypeOtuC4PA(721),
                  ifTypeOtuC5PA(722),
                  ifTypeOtuC6PA(723),
                  ifTypeF25781(725),
                  ifTypeOtuC7PA(726),
                  ifTypeOtuC8PA(727),
                  ifTypeOtuC9PA(728),
                  ifTypeOtuC10PA(729),
                  ifTypeOtuC11PA(730),
                  ifTypeOtuC12PA(731),
                  ifTypeOtlC1PA(732),
                  ifTypeOtlC2PA(733),
                  ifTypeOtlC2P5A(734),
                  ifTypeOtlC3PA(735),
                  ifTypeOtlC3P5A(736),
                  ifTypeOtlC4PA(737),
                  ifTypeOtlC4P5A(738),
                  ifTypeOtlC5PA(739),
                  ifTypeOtlC5P5A(740),
                  ifTypeOtlC6PA(741),
                  ifType400GbE(742),
                  ifTypeOtsi(744),
                  ifTypeOtuC2(745),
                  ifTypeOtuC3(746),
                  ifTypeOtuC4(747),
                  ifType64GFC(753),
                  ifTypeRng(754),
                  ifTypePkcs11(755),
                  ifTypeIlkLanes(756),
                  ifTypeF24330(757),
    grpffpCh(1000),
    grpffpOm(1001),
    grpCrsDcn(1002),
    grpLanDcn(1003),
    grpConn(1004),
    grpffpVchN(1005),
    grpVirtualConn(1006),
    conFanContainer(1101),
    conModContainer(1102),
    conPlugContainer(1103),
    grpCrsCh(1104),
    physTermPoint(1105),
    virtualTermPoint(1106),
    fanContainer(1107),
    protectionCable(1108),
    filterCable(1109),
    groupTermPoint(1110)
                }

FspR7EPCConfig ::= TEXTUAL-CONVENTION
  STATUS        current
  DESCRIPTION
        "Error Propagation Code Configuration"
  SYNTAX    INTEGER
        {
            undefined(0),
            nos(1),
            idle(3)
        }

FspR7EPCConfigCaps ::= TEXTUAL-CONVENTION
  STATUS        current
  DESCRIPTION
        "Error Propagation Code Configuration"
  SYNTAX    BITS
        {
            capUndefined(0),
            capNos(1),
            capIdle(3)
        }

FspR7ErrorFwdMode ::= TEXTUAL-CONVENTION
  STATUS        current
  DESCRIPTION
        "Determines the reaction in forward direction in response to a LOS on
        the interface on the opposite side of the module: may override
        this behaviour in the interests of laser safety."
  SYNTAX    INTEGER
        {
            undefined(0),
            ais(1), --Setting of all-ones AIS: Only relevant to a SONET / SDH / OTU interface
            epc(2), --Error Propagation Code is set, - if available, - for other applications, - if so desired, - only settable where available
            idle(3), --In the absence of any other indication, such as ALS, this implies a typical ADVA network-side facility behavior; or Idle insertion (Amazon)
            lsrOff(4), --Where no Error Propagation Code is available, - or if so desired
            lsrBrk(5), --Laser Break. Break of x[ms] length in client signal upon detection of error to propagate the error condition.
            txOff(6), --Used for electrical SFP similar than LSROFF
            losFwd(7) --Turn off client LASER on network LOS (only); special case
        }

FspR7ErrorFwdModeCaps ::= TEXTUAL-CONVENTION
  STATUS        current
  DESCRIPTION
        "Determines the reaction in forward direction in response to a LOS on
        the interface on the opposite side of the module: may override
        this behaviour in the interests of laser safety."
  SYNTAX    BITS
        {
            capUndefined(0),
            capAis(1),
            capEpc(2),
            capIdle(3),
            capLsrOff(4),
            capLsrBrk(5),
            capTxOff(6),
            capLosFwd(7)
        }

FspR7EthernetEpcConfig ::= TEXTUAL-CONVENTION
  STATUS        current
  DESCRIPTION
        "Ethernet Error Propagation Code Configuration"
  SYNTAX    INTEGER
        {
            undefined(0),
            locFlt(1),
            idle(2)
        }

FspR7EthernetEpcConfigCaps ::= TEXTUAL-CONVENTION
  STATUS        current
  DESCRIPTION
        "Ethernet Error Propagation Code Configuration"
  SYNTAX    BITS
        {
            capUndefined(0),
            capLocFlt(1),
            capIdle(2)
        }

FspR7FanMode ::= TEXTUAL-CONVENTION
  STATUS        current
  DESCRIPTION
        "Required CEM fan speed"
  SYNTAX    INTEGER
        {
            undefined(0),
            eco(1), --Economic (low fan rpm)
            high1(2) --High1 (high1 fan rpm)
        }

FspR7FalseTrue ::= TEXTUAL-CONVENTION
  STATUS        current
  DESCRIPTION
        "False True variable."
  SYNTAX    INTEGER
        {
            undefined(0),
            false(1),
            true(2)
        }

FspR7FDStatus ::= TEXTUAL-CONVENTION
  STATUS        current
  DESCRIPTION
        "Fiber Detect Status"
  SYNTAX    INTEGER
        {
            undefined(0),
            enabled(1),
            disabledSystem(2),
            disabledModule(3),
            disabledPtp(4),
            disabledAdmin(5)
        }

FspR7FDStatusCaps ::= TEXTUAL-CONVENTION
  STATUS        current
  DESCRIPTION
        "Fiber Detect Status"
  SYNTAX    BITS
        {
            capUndefined(0),
            capEnabled(1),
            capDisabledSystem(2),
            capDisabledModule(3),
            capDisabledPtp(4),
            capDisabledAdmin(5)
        }

FspR7FecType ::= TEXTUAL-CONVENTION
  STATUS        current
  DESCRIPTION
        "Forward Error Correction (Only relevant where TYPE = OTU#)"
  SYNTAX    INTEGER
        {
            undefined(0),
            gFec(1), --G709 Standard FEC
            eFec(2), --Enhanced FEC
            noFec(3), --No FEC
            eFec1(4), --Enhanced FEC (INTEL)
            eFec2(5), --Enhanced FEC (AMCC)
            eFec3(6), --Enhanced FEC (CORE)
            eFec4(7), --Enhanced FEC (Acacia)
            eFecX(8), --Variable Coding Gain
            eFec5(9), --Cascaded FEC (LDPC+GFEC)
            eFec6(10), --EFEC-6 (Turbo)
            eFec7(11), --EFEC-7 (15% Overhead)
            eFec8(12), --EFEC-8 (25% Overhead)
            rsFec2(13), --RSFEC-2(802.3 Clause 91)
            eFec9(14), --EFEC-9 (25% OH w/low LT)
            eFec10(15), --EFEC-10
            eFec11(16), --EFEC-11
            eFec12(17), --EFEC-12
            eFec13(18), --EFEC-13
            eFec14(19), --EFEC-14
            eFec15(20), --EFEC-15
            rs528(21), --Reed-Solomon(528,514)
            rs544(22), --RS544
            scFec(23), --StairCase FEC
            oFec(24), --Reed-Solomon OFEC
            eFec16(25), --EFEC-16
            fecSdb20(26), --FEC-SDB20
            cFec(27) --Ethernet IEEE802.3ct and OIF 400G ZR CFEC
        }

FspR7FecTypeCaps ::= TEXTUAL-CONVENTION
  STATUS        current
  DESCRIPTION
        "Forward Error Correction (Only relevant where TYPE = OTU#)"
  SYNTAX    BITS
        {
            capUndefined(0),
            capGFec(1),
            capEFec(2),
            capNoFec(3),
            capEFec1(4),
            capEFec2(5),
            capEFec3(6),
            capEFec4(7),
            capEFecX(8),
            capEFec5(9),
            capEFec6(10),
            capEFec7(11),
            capEFec8(12),
            capRsFec2(13),
            capEFec9(14),
            capEFec10(15),
            capEFec11(16),
            capEFec12(17),
            capEFec13(18),
            capEFec14(19),
            capEFec15(20),
            capRs528(21),
            capRs544(22),
            capScFec(23),
            capOFec(24),
            capEFec16(25),
            capFecSdb20(26),
            capCFec(27)
        }

FspR7FiberBrand ::= TEXTUAL-CONVENTION
  STATUS        current
  DESCRIPTION
        "Brand of fiber present in the fiber plant"
  SYNTAX    INTEGER
        {
            undefined(0),
            g652(1),
            g653(2),
            g655(3),
            smf28e(4),
            allWave(5),
            leaf(6),
            twRs(7),
            twPl(8),
            twCl(9),
            teraLight(10),
            smfLs(11),
            metrocor(12)
        }

FspR7FiberBrandCaps ::= TEXTUAL-CONVENTION
  STATUS        current
  DESCRIPTION
        "Brand of fiber present in the fiber plant"
  SYNTAX    BITS
        {
            capUndefined(0),
            capG652(1),
            capG653(2),
            capG655(3),
            capSmf28e(4),
            capAllWave(5),
            capLeaf(6),
            capTwRs(7),
            capTwPl(8),
            capTwCl(9),
            capTeraLight(10),
            capSmfLs(11),
            capMetrocor(12)
        }

FspR7FilterShape ::= TEXTUAL-CONVENTION
  STATUS        current
  DESCRIPTION
        "Filter shape"
  SYNTAX    INTEGER
        {
            undefined(0),
            none(1),
            rrcosne(2),
            rcosne(3),
            narrow(4)
        }

FspR7FilterShapeCaps ::= TEXTUAL-CONVENTION
  STATUS        current
  DESCRIPTION
        "Filter shape"
  SYNTAX    BITS
        {
            capUndefined(0),
            capNone(1),
            capRrcosne(2),
            capRcosne(3),
            capNarrow(4)
        }

FspR7FlowControlMode ::= TEXTUAL-CONVENTION
  STATUS        current
  DESCRIPTION
        "Flow Control mechanism"
  SYNTAX    INTEGER
        {
            undefined(0),
            none(1),
            hwControl(2),
            pause(3) --Pause frame generation.
        }

FspR7FlowControlModeCaps ::= TEXTUAL-CONVENTION
  STATUS        current
  DESCRIPTION
        "Flow Control mechanism"
  SYNTAX    BITS
        {
            capUndefined(0),
            capNone(1),
            capHwControl(2),
            capPause(3)
        }

FspR7ForcedStatus ::= TEXTUAL-CONVENTION
  STATUS        current
  DESCRIPTION
        "Forced Destroy"
  SYNTAX    INTEGER
        {
            undefined(0),
            active(1),
            forcedDestroy(2)
        }

FspR7ForcedStatusCaps ::= TEXTUAL-CONVENTION
  STATUS        current
  DESCRIPTION
        "Forced Destroy"
  SYNTAX    BITS
        {
            capUndefined(0),
            capActive(1),
            capForcedDestroy(2)
        }

FspR7FrameFormat ::= TEXTUAL-CONVENTION
  STATUS        current
  DESCRIPTION
        "Frame Format"
  SYNTAX    INTEGER
        {
            undefined(0),
            otn(1),
            sdh(2),
            sonet(3),
            ethernet(4),
            fiberchannel(5),
            infiniband(6),
            couplinglink(7),
            transparent(8),
            notDefined(99)
        }

FspR7FrameFormatCaps ::= TEXTUAL-CONVENTION
  STATUS        current
  DESCRIPTION
        "Frame Format"
  SYNTAX    BITS
        {
            capUndefined(0),
            capOtn(1),
            capSdh(2),
            capSonet(3),
            capEthernet(4),
            capFiberchannel(5),
            capInfiniband(6),
            capCouplinglink(7),
            capTransparent(8),
            capNotDefined(99)
        }

FspR7FunctionCrs ::= TEXTUAL-CONVENTION
  STATUS        current
  DESCRIPTION
        "Describes the Cross Connect Functionality"
  SYNTAX    INTEGER
        {
            undefined(0),
            add(1),
            drop(2),
            pass(3),
            hairpin(4),
            select(5),
            addDrop(6),
            dropCont(7)
        }

FspR7FunctionCrsCaps ::= TEXTUAL-CONVENTION
  STATUS        current
  DESCRIPTION
        "Describes the Cross Connect Functionality"
  SYNTAX    BITS
        {
            capUndefined(0),
            capAdd(1),
            capDrop(2),
            capPass(3),
            capHairpin(4),
            capSelect(5),
            capAddDrop(6),
            capDropCont(7)
        }

FspR7FwpDownloadMode ::= TEXTUAL-CONVENTION
  STATUS        current
  DESCRIPTION
        "FWP download mode to NCU"
  SYNTAX    INTEGER
        {
            undefined(0),
            all(1),
            required(2)
        }

FspR7Gain ::= TEXTUAL-CONVENTION
  STATUS        current
  DESCRIPTION
        "Gain"
  SYNTAX    INTEGER
        {
            undefined(0),
            gain24(1),
            gain25(2)
        }

FspR7GainCaps ::= TEXTUAL-CONVENTION
  STATUS        current
  DESCRIPTION
        "Gain"
  SYNTAX    BITS
        {
            capUndefined(0),
            capGain24(1),
            capGain25(2)
        }

FspR7GainRange ::= TEXTUAL-CONVENTION
  STATUS        current
  DESCRIPTION
        "EDFA gain range to provision"
  SYNTAX    INTEGER
        {
            undefined(0),
            high(1),
            low(2),
            lowUNlowNU(3)
        }

FspR7GainRangeCaps ::= TEXTUAL-CONVENTION
  STATUS        current
  DESCRIPTION
        "EDFA gain range to provision"
  SYNTAX    BITS
        {
            capUndefined(0),
            capHigh(1),
            capLow(2),
            capLowUNlowNU(3)
        }

FspR7GccUsage ::= TEXTUAL-CONVENTION
  STATUS        current
  DESCRIPTION
        "GCC Usage"
  SYNTAX    INTEGER
        {
            undefined(0),
            dcn(1),
            crypto(2)
        }

FspR7GccUsageCaps ::= TEXTUAL-CONVENTION
  STATUS        current
  DESCRIPTION
        "GCC Usage"
  SYNTAX    BITS
        {
            capUndefined(0),
            capDcn(1),
            capCrypto(2)
        }

FspR7GropticsType ::= TEXTUAL-CONVENTION
  STATUS        current
  DESCRIPTION
        "Identification of the desired group optics inorder to verify the plug types are as expected"
  SYNTAX    INTEGER
        {
            undefined(0),
            sr4(1),
            lr4(2),
            user(3),
            sr10(4)
        }

FspR7GropticsTypeCaps ::= TEXTUAL-CONVENTION
  STATUS        current
  DESCRIPTION
        "Identification of the desired group optics inorder to verify the plug types are as expected"
  SYNTAX    BITS
        {
            capUndefined(0),
            capSr4(1),
            capLr4(2),
            capUser(3),
            capSr10(4)
        }

FspR7Integer32Caps ::= TEXTUAL-CONVENTION
  DISPLAY-HINT        "4d:4d"
  STATUS        current
  DESCRIPTION
        "A FspR7Integer32Caps specification.
        1..4 bytes - minValue(Integer32),
        5..8 bytes - maxValue(Integer32)."
  SYNTAX    OCTET STRING (SIZE(0..8))

FspR7InterfaceCrossover ::= TEXTUAL-CONVENTION
  STATUS        current
  DESCRIPTION
        "Medium-dependent interface crossover"
  SYNTAX    INTEGER
        {
            undefined(0),
            auto(1),
            cross(2),
            straight(3)
        }

FspR7InterfaceCrossoverCaps ::= TEXTUAL-CONVENTION
  STATUS        current
  DESCRIPTION
        "Medium-dependent interface crossover"
  SYNTAX    BITS
        {
            capUndefined(0),
            capAuto(1),
            capCross(2),
            capStraight(3)
        }

FspR7InterfaceFunction ::= TEXTUAL-CONVENTION
  STATUS        current
  DESCRIPTION
        "Interface Function"
  SYNTAX    INTEGER
        {
            undefined(0),
            transport(1),
            switch(2),
            edfa(3),
            super(4),
            passive(5),
            active(6),
            raman(7),
            physicalTerm(8),
            passThrough(9),
            addDrop(10),
            osc(11)
        }

FspR7InterfaceType ::= TEXTUAL-CONVENTION
  STATUS        current
  DESCRIPTION
        "The TYPE defines the transport service type as wrapper with wrapper layer termination OR else as payload"
  SYNTAX    INTEGER
        {
            undefined(0),
            ifTypeOtu1(1), --OTU1: Line Rate 2.66 Gbps; supports full protocol
            ifTypeOtu2(2), --OTU2: Line Rate 10.70 Gbps; supports full protocol
            ifType10GbE(3), --Ethernet 10G LAN: Line Rate 10.3125 Gbps; supports full protocol
            ifTypeOc192(4), --SONET OC-192: Line Rate 9.953 Gbps; supports full protocol
            ifTypeOc48(5), --SONET OC-48: Line Rate 2.488 Gbps; supports full protocol
            ifTypeStm16(6), --SDH STM-16: Line Rate 2.488 Gbps; supports full protocol
            ifTypeStm64(7), --SDH STM-16: Line Rate 9.953 Gbps; supports full protocol
            ifType10GFC(8), --Fibre Channel 10G: Line Rate 10.518 Gbps; supports full protocol
            ifTypeF1062(10), --Fixed Rate 1.062 Gbps; supports transport of Fibre Channel 1G
            ifTypeF1250(11), --Fixed Rate 1.250 Gbps; supports transport of Ethernet 1G 
            ifTypeFC(12), --Fibre Channel 1G: Line Rate 1.0625 Gbps; supports full protocol
            ifTypeF125(13), --Fixed Rate 125 Mbps; supports transport of Fast Ethernet or MADI 
            ifTypeF200(14), --Fixed Rate 200 Mbps; supports transport of ESCON
            ifTypeF9953(15), --Fixed Rate 9.953 Gbps; supports transport of STM-64, OC-192 or 10G Ethernet WAN
            ifTypeF10312(16), --Fixed Rate 10.312 Gbps; supports transport of Ethernet 10G LAN
            ifTypeF10518(17), --Fixed Rate 10.518 Gbps; supports transport of Fibre Channel 10G
            ifTypeF2488(18), --Fixed Rate 2.488 Gbps; supports transport of STM-16 or OC-48
            ifTypeGfpF(19), --GFP-F: Generic Framing Protocol Frame (payload has a defined frame)
            ifTypeGfpT(20), --GFP-T: Generic Framing Protocol Transparent (payload is transparent)
            ifTypeDccL(21), --SONET Line DCC: Digital Communication Channel in overhead bytes
            ifTypeDccS(22), --SONET Section DCC: Digital Communication Channel in overhead bytes
            ifTypeDccP(23), --SONET Path DCC: Digital Communication Channel in overhead bytes
            ifTypeOdu1(24), --ODU1: carries client service
            ifTypeGcc0(25), --GCC0: General Communication Channel 0 in overhead bytes
            ifTypeGcc1(26), --GCC1: General Communication Channel 1 in overhead bytes
            ifTypeGcc2(27), --GCC2: General Communication Channel 2 in overhead bytes
            ifTypeoch(28), --Single optical channel on physical layer
            ifTypeOm(29), --Multiplex of optical channels on physical layer
            ifTypeOt(34), --Multiplex of optical channels on physical layer with OSC support
            ifTypeE10or100bt(36), --Ethernet 10/100Base-T: Ethernet 10 or 100 Mbps on electrical physical layer
            ifTypeE100fx(37), --Ethernet 100FX: Ethernet 100 Mbps optical physical layer
            ifTypeCl(38), --Coupling Link 1G: Inter System Channel 
            ifType2GFC(39), --Fibre Channel 2G: Line Rate 2.125 Gbps; supports full protocol
            ifType2GCL(40), --Coupling Link 2G: Inter System Channel 
            ifType1GbE(41), --Ethernet 1G: Line Rate 1.03125 Gbps; supports full protocol
            ifTypeEoc(42), --Embedded Operations Channel; supports management communication 
            ifTypeSwitch(43), --Switch; supports path switching
            ifTypePassive(44), --Passive; fixed equipment path
            ifTypeF2500(45), --Fixed Rate 2.500 Mbps; supports transport of 2.5G Infiniband
            ifTypeSc(46), --Supervisiory Channel (OSC); supports management communication
            ifTypeUch(47), --Unidirectional Channel: Service support limited to one direction
            ifTypeF155(48), --Fixed Rate 155.52 Mbps; supports transport of SDH STM-1, SONET OC-3 or ATM 155 
            ifTypeF622(49), --Fixed Rate 622.08 Mbps; supports transport of SDH STM-4, SONET OC-12 or ATM 622 
            ifTypeF2125(50), --Fixed Rate 2.125 Gbps; supports transport for Fibre Channel 2G
            ifTypeF2666(51), --Fixed Rate 2.666 Gbps; supports transport of OTU1
            ifTypeF4250(52), --Fixed Rate 4.250 Gbps; supports transport of Fibre Channel 4G or 4TCA4G[US] proprietary network signal
            ifTypeF10709(54), --Fixed Rate 10.709 Gbps; supports transport of OTU2
            ifTypeF11095(55), --Fixed Rate 11.095 Gbps; supports transport of OTU2e (OTU2 carrying Ethernet 10G LAN with stuffing)
            ifTypeF11318(56), --Fixed Rate 11.318 Gbps; supports transport of OTU2f (OTU2 carrying Fibre Channel 10G with stuffing)
            ifTypeLs(57), --Not supported
            ifType4GFC(58), --Fibre Channel 4G: Line Rate 4.250 Gbps; supports full protocol
            ifTypeGcc0S(59), --GCC0 Special: General Communication Channel 0 Special
            ifType2R(60), --Regeneration-2R: Signal shaped and re-clocked
            ifTypePppIp(61), --Point-to-Point Protocol; connects communication channel to Management Network
            ifTypeLanIp(62), --Internet Protocol LAN; connects Management Network
            ifTypeSerial(64), --Serial Interface; supports RS-232 data format
            ifTypeModem(65), --Modem
            ifTypeAdapt(66), --Adaptive Clock: Equipment adjusts clock to any rate (within limits) to match signal
            ifTypeAdaptd(67), --Adaptive Clock Discrete: Equipment adjusts clock to a predefined rate to match signal
            ifTypeGBEFR(69), --Not supported
            ifTypeVc4(70), --SDH VC-4: carries client service 
            ifTypeVc3(71), --SDH VC-3: carries client service 
            ifTypeSts1(72), --SONET STS-1: carries client service
            ifTypeEdfa(73), --Amplified multiplex of optical channels
            ifTypeEdfaMid(74), --Amplified multiplex of optical channels access between amplifier stages
            ifType10Gdw(75), --Not supported
            ifTypeOtu2Lan(76), --OTU2 (10G Ethernet): OTU2 carrying Ethernet 10G with stuffing control)
            ifTypeOtu1Lan(77), --OTU1 (Ethernet): OTU1 carrying Ethernet 1G)
            ifTypeOtu1Fc(78), --OTU1 (Fibre Channel 1G): OTU1 carrying Fibre Channel 1G)
            ifTypeOtu1Fc2G(79), --OTU1 (Fibre Channel 2G): OTU1 carrying Fibre Channel 2G)
            ifTypeF197(80), --Fixed Rate 196.6 Mbps; supports transport of GLink
            ifTypeTif(81), --Telemetry Interface
            ifTypeSts3c(82), --SONET STS-3c: carries client service
            ifTypeVs1(83), --Virtual Container; carries client service
            ifType1GbETH(84), --Ethernet 1G-Rate Limit: Rate limited Ethernet at 1Gbps or lower
            ifTypeStm1(85), --SDH STM-1: Line Rate 155.52 Mbps; supports full protocol
            ifTypeStm4(86), --SDH STM-4: Line Rate 622.08 Mbps; supports full protocol
            ifTypeOc3(87), --SONET OC-3: Line Rate 155.52 Mbps; supports full protocol
            ifTypeOc12(88), --SONET OC-12: Line Rate 622.08 Mbps; supports full protocol
            ifTypeOtu1Stm1(89), --OTU1 (STM1): OTU1 carrying STM-1
            ifTypeOtu1Stm4(90), --OTU1 (STM4): OTU1 carrying STM-4
            ifTypeF166(91), --Fixed Rate 166 Mbps; supports transport of Video
            ifTypeF666(92), --Fixed Rate 666 Mbps; supports transport of Video
            ifTypeI2C(93), --I2C: Inter-Integrated Circuit 
            ifTypeLifIP(94), --LIF IP: Logiical Interface to support Internet Protocol (IP)
            ifTypeSts24c(95), --SONET STS-24c: carries client service
            ifTypeSts48c(96), --SONET STS-48c: carries client service
            ifTypeLifte(97), --Traffic Engineering: Logical Interface to support network traffic engineering
            ifTypeRaman(98), --Amplified multiplex of optical channels using recieve network fiber
            ifTypeIpWhiteList(99), --IP (White List): Internet Protocol (IP) allowed packets
            ifTypeOspfIp(100), --IP (OSPF): Internet Protocol (IP) supports Open Shortest Path First (OSPF) path determination
            ifTypeEncapIp(101), --IP (Encapsulation): Internet Protocol (IP) allows IP packets to be encapsulated within an IP packet 
            ifTypeOtu3(102), --OTU3: Line Rate 43.01 Gbps; supports full protocol
            ifTypeStm256(103), --SDH STM-256: Line Rate 39.81312 Gbps; supports full protocol
            ifTypeOc768(104), --SONET OC-768: Line Rate 39.81312 Gbps; supports full protocol
            ifTypeF10664(105), --Fixed Rate 10.664 Gbps; supports transport of proprietary OTU2 carrying STM-64 or OC-192 without stuffing
            ifTypeOdu2(106), --ODU2: carries client service
            ifTypeF39813(107), --Fixed Rate 39.813 Gbps; supports transport of OC-768 or STM-256 
            ifTypeVc4c8(108), --SDH VC4-8c; carries client service
            ifTypeVc4c16(109), --SDH VC4-16c; carries client service
            ifTypeF8500(110), --Fixed datarate 8500 Mbps; supports transport of 8G Fibre Channel
            ifTypePb(111), --Port Binding: support port specification for TCP and UDP
            ifTypePolicer(112), --Police: support Ethernet packet monitoring and control
            ifTypeQueue(113), --Queue: support Ethernet packet queueing
            ifTypeFlowPoint(114), --Flow: carreis client service
            ifTypeLag(115), --Link Aggregation Group: Multiple ports support traffic sharing
            ifTypeElinePPP(116), --Ethernet path restricted to another point
            ifTypeEtree(117), --Ethernet Tree
            ifTypeEline(118), --Ethernet path restricted to another point
            ifTypeElan(119), --Ethernet path forms a LAN
            ifTypeCtrans(120),
            ifTypeVs0(121), --Virtual Sub Container (VS0): carries client service
            ifTypeTug(122), --Triburary Unit Group: carries client service
            ifTypeMd(123), --Maintenance Domain
            ifTypeMa(124), --Maintenance Association
            ifTypeDownMep(125), --Downstream Maintenance End Point
            ifTypeFMep(126), --Far End Maintenance End Point
            ifType8GFC(127), --Fibre Channel 8G: Line Rate 8.5 Gbps; supports full protocol
            ifType10Gib(128), --InfiniBand 10G: Line Rate 10.000 Gbps; supports full protocol
            ifTypeF10000(129), --Fixed Rate 10000 Mbps; supports transport of InifinBand 10G
            ifTypeOtu2pFC8(130), --Proprietary OTU2 carrying Fibre Channel 8G
            ifTypeOtu2pIB(131), --Proprietary OTU2 carrying Infiniband 10G
            ifTypeOtu2pFC(132), --Proprietary OTU2 carrying Fibre Channel 10G
            ifTypeOtu2pLAN(133), --Proprietary OTU2 carrying Ethernet 10G
            ifTypeOtu2p(134), --Proprietary OTU2 carrying Multiplexed Signals
            ifTypeUpMep(135), --Upstream Maintenance End Point
            ifTypeOtdrCh(136), --Optical channel supporting fiber validation
            ifTypeMaNet(137), --Maintenance Association Network
            ifTypeMaComp(138), --Maintenance Association Component
            ifTypeBridge(139), --Ethernet Bridge
            ifType1000BaseT(140), --Ethernet 1000Base-T: Ethernet 1 Gbps on electrical physical layer
            ifTypeOtu2E(141), --OTU2E: OTU2 overclocked to carry Ethernet 10G with stuffing; supports full protocol
            ifTypeOtu1E(142), --OTU1E: OTU2 overclocked to carry Ethernet 10G without stuffing; supports full protocol
            ifTypeOtu2F(143), --OTU2 carrying Fibre Channel 10G; supports full protocol
            ifTypeF11049(144), --Fixed Rate 11.049 Gbps; supports transport of OTU1E (OTU2 carrying 10G Ethernet without stuffing)
            ifTypeLifteNum(145), --Logical Interface to support Traffic Engineering across numbered IP interfaces
            ifTypeLifteUnn(146), --Logical Interface to support Traffic Engineering across unnumbered IP interfaces
            ifTypeLifPbNum(147), --Logical Interface to support Port Binding across numbered IP interfaces
            ifTypeLifSubUnn(148), --Logical Interface to support Traffic Engineering on a sublayer across unnumbered IP interfaces
            ifType5Gib(149), --InfiniBand 5G: Line Rate 5.000 Gbps; supports full protocol
            ifTypeF5000(150), --Fixed Rate 5.000 Gbps; supports transport of InfiniBand 5G
            ifTypeOtu2eEth(151), --OTU2E: OTU2 overclocked to carry Ethernet with stuffing; supports full protocol
            ifTypeOdu0(152), --ODU0: carries client service
            ifTypeFcu(153), --Fan Control
            ifTypeOtu4(154), --OTU4: Line Rate 112 Gbps; supports full protocol
            ifType100GbE(160), --Ethernet 100G: Line Rate 103.125 Gbps; supports full protocol
            ifTypeOptical(161), --Optical Channel 
            ifType10GbEWan(162), --Ethernet 10G WAN: Line Rate 9.9533 Gbps; 
            ifType10GbELan(163), --Ethernet 10G LAN: Line Rate 10.3125 Gbps; supports full protocol
            ifTypeOduFlx(164), --ODUflex: carries client service 
            ifTypeOtlc(165), --Optical Transport Lane (G.709)
            ifTypeOtu2ps(167), --Proprietary OTU2 carrying 9.953 G signal (OC-192 or STM-64)
            ifTypeOdu2E(168), --ODU2E: carries client service 
            ifTypeOdu1E(169), --ODU1E: carries client service 
            ifTypeOdu2Lan(170), --ODU2LAN: carries client service 
            ifTypeOdu4(171), --ODU4: carries client service 
            ifTypeLifVTeNum(173), --Logical Interface for Virtural Traffic Engineering links with numbered IP interfaces 
            ifTypeLifVTeUnn(174), --Logical Interface for Virtural Traffic Engineering links with unnumbered IP interfaces 
            ifTypeF14025(178), --Fixed Rate 14.025 Gbps; supports transport of Fibre Channel 16G 
            ifTypeF270(181), --Fixed Rate 270 Mbps; support transport of SD-SDI Video per SMPTE 259M-C 
            ifTypeF1485(184), --Fixed Rate 1.485 Gbps; support transport of HD-SDI Video
            ifTypeF2970(185), --Fixed Rate 2.970 Gbps; support transport of 3G-SDI Video
            ifTypeF1483(188), --Fixed Rate 1.483 Gbps; supports transport of HD-SDI Video (1)
            ifTypeF2967(189), --Fixed Rate 2.967 Gbps; supports transport of 3G-SDI Video (1)
            ifType40GbE(192), --Ethernet 40G: Line Rate 41.250; supports full protocol
            ifTypeOdu3(193), --ODU3: carries client service 
            ifTypeF41250(194), --Fixed Rate 41.250 Gbps; supports transport of Ethernet 40G (40 GbE)
            ifTypeF103125(195), --Fixed Rate 103.125 Gbps; supports transport of Ethernet 100G (100 GbE)
            ifType16GFC(196), --Fibre Channel 16G: Line Rate 14.025 Gbps; supports full protocol
            ifTypeF1228(199), --Fixed Rate 1.228 Gbps; supports transport of 2xCPRI
            ifTypeF2457(200), --Fixed Rate 2.457 Gbps; supports transport of 4xCPRI
            ifTypeF3072(201), --Fixed Rate 3.072 Gbps; support transport of 5xCPRI or 4xOBSAI
            ifTypeF4915(202), --Fixed Rate 4.915 Gbps; supports transport of 8xCPRI
            ifTypeF6144(203), --Fixed Rate 6.144 Gbps; supports transport of 10xCPRI or 8xOBSAI
            ifTypeF9830(204), --Fixed Rate 9.830 Gbps; supports transport of 16xCPRI
            ifTypeF10137(205), --Fixed Rate 10.137 Gbps; supports transport of 20xCPRI
            ifTypeAdapt1485(207), --Adaptive Clock; rates around 1.485 Gbps
            ifTypeAdapt2970(208), --Adaptive Clock; rates around 2.970 Gbps
            ifTypeOtuC2PA(209), --Proprietary OTU for 200 Gbps transports two ODU4
            ifTypeOtuC3PA(210), --Proprietary OTU for 300 Gbps transports three ODU4 over two transport lanes
            ifTypeOtuC1P5A(211), --Proprietary Optical Transport Lane at 150 Gbps
            ifTypeE10to1000t(212), --Ethernet 10/100/1000Base-T:10/100/1000 Mbps on electrical physical layer
            ifTypeLldp(213), --Link Layer Discovery Protocol
            ifType25GbE(214), --Ethernet 25G LAN
            ifType32GFC(215), --Fibre Channel 32G: Line Rate 28.05 Gbps
            ifTypeHdPppIp(220), --Point-to-Point Protocol; connects communication channel to Management Network
            ifTypeOtuC4PA(221), --Proprietary OTU for 400 Gbps transports four ODU4
            ifTypeOtuC5PA(222), --Proprietary OTU for 500 Gbps transports five ODU4
            ifTypeOtuC6PA(223), --Proprietary OTU for 600 Gbps transports six ODU4
            ifTypeF25781(225), --Ethernet 25G: Line Rate 25.781 Gbps
            ifTypeOtuC7PA(226), --Proprietary OTU for 700 Gbps transports seven ODU4
            ifTypeOtuC8PA(227), --Proprietary OTU for 800 Gbps transports eight ODU4
            ifTypeOtuC9PA(228), --Proprietary OTU for 900 Gbps transports nine ODU4
            ifTypeOtuC10PA(229), --Proprietary OTU for 1000 Gbps transports ten ODU4
            ifTypeOtuC11PA(230), --Proprietary OTU for 1100 Gbps transports eleven ODU4
            ifTypeOtuC12PA(231), --Proprietary OTU for 1200 Gbps transports twelve ODU4
            ifTypeOtlC1PA(232), --Proprietary Optical Transport Lane at 100 Gbps
            ifTypeOtlC2PA(233), --Proprietary Optical Transport Lane at 200 Gbps
            ifTypeOtlC2P5A(234), --Proprietary Optical Transport Lane at 250 Gbps
            ifTypeOtlC3PA(235), --Proprietary Optical Transport Lane at 300 Gbps
            ifTypeOtlC3P5A(236), --Proprietary Optical Transport Lane at 350 Gbps
            ifTypeOtlC4PA(237), --Proprietary Optical Transport Lane at 400 Gbps
            ifTypeOtlC4P5A(238), --Proprietary Optical Transport Lane at 450 Gbps
            ifTypeOtlC5PA(239), --Proprietary Optical Transport Lane at 500 Gbps
            ifTypeOtlC5P5A(240), --Proprietary Optical Transport Lane at 550 Gbps
            ifTypeOtlC6PA(241), --Proprietary Optical Transport Lane at 600 Gbps
            ifType400GbE(242), --Ethernet 400G: Line Rate 425 Gbit/s (400GE with 802.3cm PAM4 on 4 optical lanes with 4x53.125GBd)
            ifTypeOtsi(244), --Optical Tributary Signal
            ifTypeOtuC2(245), --OTUC2 carriers ODUC2 with 200 Gbps payload
            ifTypeOtuC3(246), --OTUC3 carriers ODUC3 with 300 Gbps payload
            ifTypeOtuC4(247), --OTUC4 carriers ODUC4 with 400 Gbps payload
            ifType64GFC(253), --Fibre Channel 64G: Line Rate 57.8 Gbps
            ifTypeRng(254), --JavaCard Applet
            ifTypePkcs11(255), --JavaCard Applet
            ifTypeIlkLanes(256), --Layer rate Interlaken (chip-to-chip interconnection protocol)
            ifTypeF24330(257) --Fixed Rate 24.330 Gbps; supports transport of CPRI Rate-10
        }

FspR7InterfaceTypeCaps ::= TEXTUAL-CONVENTION
  STATUS        current
  DESCRIPTION
        "The TYPE defines the transport service type as wrapper with wrapper layer termination OR else as payload"
  SYNTAX    BITS
        {
            capUndefined(0),
            capIfTypeOtu1(1),
            capIfTypeOtu2(2),
            capIfType10GbE(3),
            capIfTypeOc192(4),
            capIfTypeOc48(5),
            capIfTypeStm16(6),
            capIfTypeStm64(7),
            capIfType10GFC(8),
            capIfTypeF1062(10),
            capIfTypeF1250(11),
            capIfTypeFC(12),
            capIfTypeF125(13),
            capIfTypeF200(14),
            capIfTypeF9953(15),
            capIfTypeF10312(16),
            capIfTypeF10518(17),
            capIfTypeF2488(18),
            capIfTypeGfpF(19),
            capIfTypeGfpT(20),
            capIfTypeDccL(21),
            capIfTypeDccS(22),
            capIfTypeDccP(23),
            capIfTypeOdu1(24),
            capIfTypeGcc0(25),
            capIfTypeGcc1(26),
            capIfTypeGcc2(27),
            capIfTypeoch(28),
            capIfTypeOm(29),
            capIfTypeOt(34),
            capIfTypeE10or100bt(36),
            capIfTypeE100fx(37),
            capIfTypeCl(38),
            capIfType2GFC(39),
            capIfType2GCL(40),
            capIfType1GbE(41),
            capIfTypeEoc(42),
            capIfTypeSwitch(43),
            capIfTypePassive(44),
            capIfTypeF2500(45),
            capIfTypeSc(46),
            capIfTypeUch(47),
            capIfTypeF155(48),
            capIfTypeF622(49),
            capIfTypeF2125(50),
            capIfTypeF2666(51),
            capIfTypeF4250(52),
            capIfTypeF10709(54),
            capIfTypeF11095(55),
            capIfTypeF11318(56),
            capIfTypeLs(57),
            capIfType4GFC(58),
            capIfTypeGcc0S(59),
            capIfType2R(60),
            capIfTypePppIp(61),
            capIfTypeLanIp(62),
            capIfTypeSerial(64),
            capIfTypeModem(65),
            capIfTypeAdapt(66),
            capIfTypeAdaptd(67),
            capIfTypeGBEFR(69),
            capIfTypeVc4(70),
            capIfTypeVc3(71),
            capIfTypeSts1(72),
            capIfTypeEdfa(73),
            capIfTypeEdfaMid(74),
            capIfType10Gdw(75),
            capIfTypeOtu2Lan(76),
            capIfTypeOtu1Lan(77),
            capIfTypeOtu1Fc(78),
            capIfTypeOtu1Fc2G(79),
            capIfTypeF197(80),
            capIfTypeTif(81),
            capIfTypeSts3c(82),
            capIfTypeVs1(83),
            capIfType1GbETH(84),
            capIfTypeStm1(85),
            capIfTypeStm4(86),
            capIfTypeOc3(87),
            capIfTypeOc12(88),
            capIfTypeOtu1Stm1(89),
            capIfTypeOtu1Stm4(90),
            capIfTypeF166(91),
            capIfTypeF666(92),
            capIfTypeI2C(93),
            capIfTypeLifIP(94),
            capIfTypeSts24c(95),
            capIfTypeSts48c(96),
            capIfTypeLifte(97),
            capIfTypeRaman(98),
            capIfTypeIpWhiteList(99),
            capIfTypeOspfIp(100),
            capIfTypeEncapIp(101),
            capIfTypeOtu3(102),
            capIfTypeStm256(103),
            capIfTypeOc768(104),
            capIfTypeF10664(105),
            capIfTypeOdu2(106),
            capIfTypeF39813(107),
            capIfTypeVc4c8(108),
            capIfTypeVc4c16(109),
            capIfTypeF8500(110),
            capIfTypePb(111),
            capIfTypePolicer(112),
            capIfTypeQueue(113),
            capIfTypeFlowPoint(114),
            capIfTypeLag(115),
            capIfTypeElinePPP(116),
            capIfTypeEtree(117),
            capIfTypeEline(118),
            capIfTypeElan(119),
            capIfTypeCtrans(120),
            capIfTypeVs0(121),
            capIfTypeTug(122),
            capIfTypeMd(123),
            capIfTypeMa(124),
            capIfTypeDownMep(125),
            capIfTypeFMep(126),
            capIfType8GFC(127),
            capIfType10Gib(128),
            capIfTypeF10000(129),
            capIfTypeOtu2pFC8(130),
            capIfTypeOtu2pIB(131),
            capIfTypeOtu2pFC(132),
            capIfTypeOtu2pLAN(133),
            capIfTypeOtu2p(134),
            capIfTypeUpMep(135),
            capIfTypeOtdrCh(136),
            capIfTypeMaNet(137),
            capIfTypeMaComp(138),
            capIfTypeBridge(139),
            capIfType1000BaseT(140),
            capIfTypeOtu2E(141),
            capIfTypeOtu1E(142),
            capIfTypeOtu2F(143),
            capIfTypeF11049(144),
            capIfTypeLifteNum(145),
            capIfTypeLifteUnn(146),
            capIfTypeLifPbNum(147),
            capIfTypeLifSubUnn(148),
            capIfType5Gib(149),
            capIfTypeF5000(150),
            capIfTypeOtu2eEth(151),
            capIfTypeOdu0(152),
            capIfTypeFcu(153),
            capIfTypeOtu4(154),
            capIfType100GbE(160),
            capIfTypeOptical(161),
            capIfType10GbEWan(162),
            capIfType10GbELan(163),
            capIfTypeOduFlx(164),
            capIfTypeOtlc(165),
            capIfTypeOtu2ps(167),
            capIfTypeOdu2E(168),
            capIfTypeOdu1E(169),
            capIfTypeOdu2Lan(170),
            capIfTypeOdu4(171),
            capIfTypeLifVTeNum(173),
            capIfTypeLifVTeUnn(174),
            capIfTypeF14025(178),
            capIfTypeF270(181),
            capIfTypeF1485(184),
            capIfTypeF2970(185),
            capIfTypeF1483(188),
            capIfTypeF2967(189),
            capIfType40GbE(192),
            capIfTypeOdu3(193),
            capIfTypeF41250(194),
            capIfTypeF103125(195),
            capIfType16GFC(196),
            capIfTypeF1228(199),
            capIfTypeF2457(200),
            capIfTypeF3072(201),
            capIfTypeF4915(202),
            capIfTypeF6144(203),
            capIfTypeF9830(204),
            capIfTypeF10137(205),
            capIfTypeAdapt1485(207),
            capIfTypeAdapt2970(208),
            capIfTypeOtuC2PA(209),
            capIfTypeOtuC3PA(210),
            capIfTypeOtuC1P5A(211),
            capIfTypeE10to1000t(212),
            capIfTypeLldp(213),
            capIfType25GbE(214),
            capIfType32GFC(215),
            capIfTypeHdPppIp(220),
            capIfTypeOtuC4PA(221),
            capIfTypeOtuC5PA(222),
            capIfTypeOtuC6PA(223),
            capIfTypeF25781(225),
            capIfTypeOtuC7PA(226),
            capIfTypeOtuC8PA(227),
            capIfTypeOtuC9PA(228),
            capIfTypeOtuC10PA(229),
            capIfTypeOtuC11PA(230),
            capIfTypeOtuC12PA(231),
            capIfTypeOtlC1PA(232),
            capIfTypeOtlC2PA(233),
            capIfTypeOtlC2P5A(234),
            capIfTypeOtlC3PA(235),
            capIfTypeOtlC3P5A(236),
            capIfTypeOtlC4PA(237),
            capIfTypeOtlC4P5A(238),
            capIfTypeOtlC5PA(239),
            capIfTypeOtlC5P5A(240),
            capIfTypeOtlC6PA(241),
            capIfType400GbE(242),
            capIfTypeOtsi(244),
            capIfTypeOtuC2(245),
            capIfTypeOtuC3(246),
            capIfTypeOtuC4(247),
            capIfType64GFC(253),
            capIfTypeRng(254),
            capIfTypePkcs11(255),
            capIfTypeIlkLanes(256),
            capIfTypeF24330(257)
        }

FspR7InvertTelemetryInputLogic ::= TEXTUAL-CONVENTION
  STATUS        current
  DESCRIPTION
        "Change telemetry interface input logic"
  SYNTAX    INTEGER
        {
            undefined(0),
            almClosed(1), --TIF Alarm when the switch is closed
            almOpen(2) --TIF Alarm when the switch is open
        }

FspR7InvertTelemetryInputLogicCaps ::= TEXTUAL-CONVENTION
  STATUS        current
  DESCRIPTION
        "Change telemetry interface input logic"
  SYNTAX    BITS
        {
            capUndefined(0),
            capAlmClosed(1),
            capAlmOpen(2)
        }

FspR7IpForwarding ::= TEXTUAL-CONVENTION
  STATUS        current
  DESCRIPTION
        "Enable/disable IP forwarding."
  SYNTAX    INTEGER
        {
            undefined(0),
            enable(1),
            disable(2),
            license(3)
        }

FspR7IpType ::= TEXTUAL-CONVENTION
  STATUS        current
  DESCRIPTION
        "Type of IP configuration"
  SYNTAX    INTEGER
        {
            undefined(0),
            unnumbered(1), --No additional IP parameter is needed for ECC Interface; System IP address is used
            numbered(2), --Additional IP parameter is needed for ECC Interface; Has to be setted by the user
            system(3)
        }

FspR7IpTypeCaps ::= TEXTUAL-CONVENTION
  STATUS        current
  DESCRIPTION
        "Type of IP configuration"
  SYNTAX    BITS
        {
            capUndefined(0),
            capUnnumbered(1),
            capNumbered(2),
            capSystem(3)
        }

FspR7IpMode ::= TEXTUAL-CONVENTION
  STATUS        current
  DESCRIPTION
        "IP Mode of Operation either IPv4 only or IPv4 and IPv6. When operation supports IPv6, it is used for addresses external to the network."
  SYNTAX    INTEGER
        {
            undefined(0),
            none(1),
            ipv4(2),
            ipv4ipv6(3),
            ipv6(4)
        }

FspR7IpModeCaps ::= TEXTUAL-CONVENTION
  STATUS        current
  DESCRIPTION
        "IP Mode of Operation either IPv4 only or IPv4 and IPv6. When operation supports IPv6, it is used for addresses external to the network."
  SYNTAX    BITS
        {
            capUndefined(0),
            capNone(1),
            capIpv4(2),
            capIpv4ipv6(3),
            capIpv6(4)
        }

FspR7Ipv6Address ::= TEXTUAL-CONVENTION
  DISPLAY-HINT        "2x:"
  STATUS        current
  DESCRIPTION
        "This data type is used to model IPv6 addresses.
        This is a binary string of 16 octets in network
        byte-order."
  SYNTAX    OCTET STRING (SIZE(16..16))

FspR7IPv6Type ::= TEXTUAL-CONVENTION
  STATUS        current
  DESCRIPTION
        "Type of IPv6 configuration"
  SYNTAX    INTEGER
        {
            undefined(0),
            none(1), --IPv6 not configured
            numbered(2), --Additional IPv6 parameter is needed for ECC Interface; Has to be setted by the user
            unnumbered(3) --No additional IP parameter is needed for ECC Interface; System IP address is used
        }

FspR7IPv6TypeCaps ::= TEXTUAL-CONVENTION
  STATUS        current
  DESCRIPTION
        "Type of IPv6 configuration"
  SYNTAX    BITS
        {
            capUndefined(0),
            capNone(1),
            capNumbered(2),
            capUnnumbered(3)
        }

FspR7KeyActivationStatus ::= TEXTUAL-CONVENTION
  STATUS        current
  DESCRIPTION
        "Cryptographic key activation procedure or current activity status - possible values."
  SYNTAX    INTEGER
        {
            undefined(0),
            none(1), --Key activation status undetermined (invalid status). It is ephemeral/internal status.
            ready(2), --Key is ready and inactive.
            notReady(3), --Key is not ready and inactive.
            active(4), --Key is active (in service).
            generalFail(5), --Key activation evaluation failure; reason for failure is generic/unspecific.
            keyError(6), --Key either has invalid status or its data is otherwise inconsistent.
            certError(7), --Associated certificate either is missing, has invalid status or its data is otherwise inconsistent.
            duplicateActive(8) --A duplicate of this key (possibly the original legacy key) is active.
        }

FspR7KeyActivationStatusCaps ::= TEXTUAL-CONVENTION
  STATUS        current
  DESCRIPTION
        "Cryptographic key activation procedure or current activity status - possible values."
  SYNTAX    BITS
        {
            capUndefined(0),
            capNone(1),
            capReady(2),
            capNotReady(3),
            capActive(4),
            capGeneralFail(5),
            capKeyError(6),
            capCertError(7),
            capDuplicateActive(8)
        }

FspR7KeyAlgorithm ::= TEXTUAL-CONVENTION
  STATUS        current
  DESCRIPTION
        "Cryptographic key algorithm"
  SYNTAX    INTEGER
        {
            undefined(0),
            none(1), --Kind of undefined or invalid value; its interpretation and usage depends on application/context.
            rsa(2),
            dsa(3),
            ecdsa(4),
            other(5) --Other not supported algorithm.
        }

FspR7KeyExport ::= TEXTUAL-CONVENTION
  STATUS        current
  DESCRIPTION
        "Cryptographic key export (with or without encryption). Initiates preparation of raw private key (key-pair) data."
  SYNTAX    INTEGER
        {
            undefined(0),
            none(1), --DEPRECATED
            apply(2), --DEPRECATED
            noneExport(3),
            noneErase(4),
            applyExport(5),
            applyErase(6)
        }

FspR7KeyGenStatus ::= TEXTUAL-CONVENTION
  STATUS        current
  DESCRIPTION
        "Cryptographic key data (integrity and validity) status."
  SYNTAX    INTEGER
        {
            undefined(0),
            none(1), --Key data status undetermined (invalid status). It is ephemeral/internal status.
            pending(2), --Key generation is in progress.
            okay(3), --Key generation finished successfully.
            integrityError(4), --Key data integrity check failed.
            dataUnavailable(5), --Key data missing; should not happen normally.
            generalFail(6), --Generic/unspecific key data error or generation/import procedure's failure.
            busyError(7) --Generation/import procedure failure, because of busy local resources; may try later.
        }

FspR7KeyLength ::= TEXTUAL-CONVENTION
  STATUS        current
  DESCRIPTION
        "SSL certificate key length (in bits)."
  SYNTAX    INTEGER
        {
            undefined(0),
            length2048(1),
            length4096(2)
        }

FspR7KeyLengthCaps ::= TEXTUAL-CONVENTION
  STATUS        current
  DESCRIPTION
        "SSL certificate key length (in bits)."
  SYNTAX    BITS
        {
            capUndefined(0),
            capLength2048(1),
            capLength4096(2)
        }

FspR7KeyLengthV2 ::= TEXTUAL-CONVENTION
  STATUS        current
  DESCRIPTION
        "Cryptographic key bit-length or bit-size. It is not a direct 'security level', because it depends on key algorithm in the first place."
  SYNTAX    INTEGER
        {
            undefined(0),
            none(1), --Key length is undefined. When importing private key data it means the key data is invalid or otherwise unsupported.
            len256(2), --Relevant for ECDSA only
            len384(3), --Relevant for ECDSA only
            len1024(4),
            len2048(5),
            len3072(6),
            len4096(7),
            other(8)
        }

FspR7KeyProfile ::= TEXTUAL-CONVENTION
  STATUS        current
  DESCRIPTION
        "Cryptographic key usage/application profile."
  SYNTAX    INTEGER
        {
            undefined(0),
            none(1),
            webService(2), --Key for secure web server (optionally, also web client i.e. mutual) authenication. There is corresponding certificate purpose.
            moduleAuth(3), --Key for encryption module(s) mutual authentication, during session establishment. There is corresponding certificate purpose.
            gNMI(4), --Key for secure GNMI server authentication. There is corresponding certificate purpose.
            sshClientAuth(6), --Key for SSH/SFTP client authentication. There is no corresponding certificate purpose, because there are no associated certificate involved.
            qkdClientAuth(7) --Key for QKD client authentication. There is corresponding certificate purpose.
        }

FspR7KeyRenewStatus ::= TEXTUAL-CONVENTION
  STATUS        current
  DESCRIPTION
        "Cryptographic key renewal status."
  SYNTAX    INTEGER
        {
            undefined(0),
            none(1), --Key renewal not started yet.
            pending(2), --Key renewal started but not finished yet.
            okay(3), --Key renewal finished successfully.
            resourcesError(4), --Failed to renew key due to resource restrictions.
            generalFail(5), --Key renewal failure (generic/unspecific error).
            busyError(6) --Key renewal error, because of busy local resources; may try later.
        }

FspR7KeyStorage ::= TEXTUAL-CONVENTION
  STATUS        current
  DESCRIPTION
        "Cryptographic key storage location"
  SYNTAX    INTEGER
        {
            undefined(0),
            none(1), --Key storage location is undefined. When importing private key data it means the key data is invalid or otherwise unsupported.
            ncu(2),
            hsmNcu(3) --HSM chip on NCU-3 module.
        }

FspR7LacpMode ::= TEXTUAL-CONVENTION
  STATUS        current
  DESCRIPTION
        "Enable of LACP state machine"
  SYNTAX    INTEGER
        {
            undefined(0),
            active(1),
            passive(2),
            disable(3)
        }

FspR7LacpModeCaps ::= TEXTUAL-CONVENTION
  STATUS        current
  DESCRIPTION
        "Enable of LACP state machine"
  SYNTAX    BITS
        {
            capUndefined(0),
            capActive(1),
            capPassive(2),
            capDisable(3)
        }

FspR7LacpTimeout ::= TEXTUAL-CONVENTION
  STATUS        current
  DESCRIPTION
        "Timeout of the LACP"
  SYNTAX    INTEGER
        {
            undefined(0),
            advaExtraShort(1),
            short(2),
            long(3)
        }

FspR7LacpTimeoutCaps ::= TEXTUAL-CONVENTION
  STATUS        current
  DESCRIPTION
        "Timeout of the LACP"
  SYNTAX    BITS
        {
            capUndefined(0),
            capAdvaExtraShort(1),
            capShort(2),
            capLong(3)
        }

FspR7LaneGroupInventory ::= TEXTUAL-CONVENTION
  STATUS        current
  DESCRIPTION
        "Lanel Group read from the hardware"
  SYNTAX    INTEGER
        {
            undefined(0),
            f19595f19520(1), --tunable CFP part of C-band
            f19515f19440(2), --tunable CFP part of C-band
            f19435f19360(3), --tunable CFP part of C-band
            f19355f19280(4), --tunable CFP part of C-band
            f19275f19200(5), --tunable CFP part of C-band
            f19600f19200(6), --tunable CFP part of C-band
            f19600f19125(7), --tunable CFP C-band
            f19597f19122(8), --tunable CFP C-band
            f19600f19570(9), --fix CFP
            f19560f19530(10), --fix CFP
            f19520f19490(11), --fix CFP
            f19480f19450(12), --fix CFP
            f19440f19410(13), --fix CFP
            f19400f19370(14), --fix CFP
            f19360f19330(15), --fix CFP
            f19320f19290(16), --fix CFP
            f19280f19250(17), --fix CFP
            f19240f19210(18), --fix CFP
            f19200f19170(19), --fix CFP
            f19160f19130(20), --fix CFP
            f19595f19565(21), --fix CFP
            f19555f19525(22), --fix CFP
            f19515f19485(23), --fix CFP
            f19475f19445(24), --fix CFP
            f19435f19405(25), --fix CFP
            f19395f19365(26), --fix CFP
            f19355f19325(27), --fix CFP
            f19315f19285(28), --fix CFP
            f19275f19245(29), --fix CFP
            f19235f19205(30), --fix CFP
            f19195f19165(31), --fix CFP
            f19155f19125(32) --fix CFP
        }

FspR7LaneGroupInventoryCaps ::= TEXTUAL-CONVENTION
  STATUS        current
  DESCRIPTION
        "Lanel Group read from the hardware"
  SYNTAX    BITS
        {
            capUndefined(0),
            capF19595f19520(1),
            capF19515f19440(2),
            capF19435f19360(3),
            capF19355f19280(4),
            capF19275f19200(5),
            capF19600f19200(6),
            capF19600f19125(7),
            capF19597f19122(8),
            capF19600f19570(9),
            capF19560f19530(10),
            capF19520f19490(11),
            capF19480f19450(12),
            capF19440f19410(13),
            capF19400f19370(14),
            capF19360f19330(15),
            capF19320f19290(16),
            capF19280f19250(17),
            capF19240f19210(18),
            capF19200f19170(19),
            capF19160f19130(20),
            capF19595f19565(21),
            capF19555f19525(22),
            capF19515f19485(23),
            capF19475f19445(24),
            capF19435f19405(25),
            capF19395f19365(26),
            capF19355f19325(27),
            capF19315f19285(28),
            capF19275f19245(29),
            capF19235f19205(30),
            capF19195f19165(31),
            capF19155f19125(32)
        }

FspR7LagFendState ::= TEXTUAL-CONVENTION
  STATUS        current
  DESCRIPTION
        "The Partner's state variables for the port, encoded as individual bits,
        as follows:
        Bits ordering:
        - LACP_Activity(0),
        - LACP_Timeout(1),
        - Aggregation(2),
        - Synchronization(3),
        - Collecting(4),
        - Distributing(5),
        - Defaulted(6),
        - Expired(7)"
  SYNTAX    OCTET STRING (SIZE(0..2))

FspR7LagIdFend ::= TEXTUAL-CONVENTION
  STATUS        current
  DESCRIPTION
        "LAG ID of the Partner LAG PORT parameters. Concatination of
        Operational Key, Priority and port number. Uses 4+2+4 bytes. Each byte is represented
        with 2 octets string.
        
        Port LAG ID Parameters
        field  octets  contents
        -----  ------  --------
        1_______1-4_____Key___________(ASCII e.g. '0x00AA')
        2_______5-6_____Port Priority_(ASCII e.g. '0x80')
        3_______7-10____Port Number___(ASCII e.g. '0x0002')
        
        Parameters of the LAG ID are separated by commas, e.g. '00AA,80,0002'"
  SYNTAX    OCTET STRING (SIZE(0..10))

FspR7LagPorts ::= TEXTUAL-CONVENTION
  STATUS        current
  DESCRIPTION
        "Eeach 4 bytes contain the information about the ETH Client or Network entity.
        Bytes ordering:
        - AidName(0)
        - ShelfNumber(1)
        - SlotNumber(2)
        - PortNumber(3)"
  SYNTAX    OCTET STRING (SIZE(0..200))

FspR7LagPortType ::= TEXTUAL-CONVENTION
  STATUS        current
  DESCRIPTION
        "Type/Speed of connected ports in the Link Aggregation Group"
  SYNTAX    INTEGER
        {
            undefined(0),
            type1gb(1),
            type10gb(2)
        }

FspR7LagPortTypeCaps ::= TEXTUAL-CONVENTION
  STATUS        current
  DESCRIPTION
        "Type/Speed of connected ports in the Link Aggregation Group"
  SYNTAX    BITS
        {
            capUndefined(0),
            capType1gb(1),
            capType10gb(2)
        }

FspR7LagStandby ::= TEXTUAL-CONVENTION
  STATUS        current
  DESCRIPTION
        "Eeach 4 bytes contain the information about the ETH Client or Network entity.
        Bytes ordering:
        - AidName(0)
        - ShelfNumber(1)
        - SlotNumber(2)
        - PortNumber(3)"
  SYNTAX    OCTET STRING (SIZE(0..200))

FspR7LagState ::= TEXTUAL-CONVENTION
  STATUS        current
  DESCRIPTION
        "The Actors state variables for the port, encoded as individual bits,
        as follows:
        Bits ordering:
        - LACP_Activity(0),
        - LACP_Timeout(1),
        - Aggregation(2),
        - Synchronization(3),
        - Collecting(4),
        - Distributing(5),
        - Defaulted(6),
        - Expired(7)"
  SYNTAX    OCTET STRING (SIZE(0..2))

FspR7LagSysIdFend ::= TEXTUAL-CONVENTION
  STATUS        current
  DESCRIPTION
        "Partner system part of LAG ID. Concatinated from priority and MAC.
        
        System LAG ID Parameters
        field octets contents
        -----  ------  --------
        1_______1-4_____System Priority__(ASCII e.g. '0x8000')
        2_______5-16____MAC Address______(ASCII e.g. 'AC-DE-48-03-67-80')
        
        Parameters of the LAG ID are separated by commas, e.g. '8000,AC-DE-48-03-67-80'"
  SYNTAX    OCTET STRING (SIZE(0..16))

FspR7LaserDelayTimer ::= TEXTUAL-CONVENTION
  STATUS        current
  DESCRIPTION
        "Relevant only when ERRFWD=LSROFF. Enables/disables the
        possibility to delay turning off and on the laser.
        This applies to the case when turning off the laser
        is done  as an error forwarding mechanism."
  SYNTAX    INTEGER
        {
            undefined(0),
            disable(1),
            enableLsrOffTm(2),
            enableLsrOnTm(3)
        }

FspR7LaserDelayTimerCaps ::= TEXTUAL-CONVENTION
  STATUS        current
  DESCRIPTION
        "Relevant only when ERRFWD=LSROFF. Enables/disables the
        possibility to delay turning off and on the laser.
        This applies to the case when turning off the laser
        is done  as an error forwarding mechanism."
  SYNTAX    BITS
        {
            capUndefined(0),
            capDisable(1),
            capEnableLsrOffTm(2),
            capEnableLsrOnTm(3)
        }

FspR7Length ::= TEXTUAL-CONVENTION
  STATUS        current
  DESCRIPTION
        "Length"
  SYNTAX    INTEGER
        {
            undefined(0),
            length37cm(5),
            length50cm(1),
            length100cm(2),
            length300cm(3),
            length500cm(4),
            length1000cm(6)
        }

FspR7LengthCaps ::= TEXTUAL-CONVENTION
  STATUS        current
  DESCRIPTION
        "Length"
  SYNTAX    BITS
        {
            capUndefined(0),
            capLength37cm(5),
            capLength50cm(1),
            capLength100cm(2),
            capLength300cm(3),
            capLength500cm(4),
            capLength1000cm(6)
        }

FspR7LicenseFilesInstall ::= TEXTUAL-CONVENTION
  STATUS        current
  DESCRIPTION
        "Installs license from files when license policy is Node"
  SYNTAX    INTEGER
        {
            undefined(0),
            rls(1),
            opr(2),
            rel(3)
        }

FspR7LicenseFilesInstallCaps ::= TEXTUAL-CONVENTION
  STATUS        current
  DESCRIPTION
        "Installs license from files when license policy is Node"
  SYNTAX    BITS
        {
            capUndefined(0),
            capRls(1),
            capOpr(2),
            capRel(3)
        }

FspR7LicenseManagement ::= TEXTUAL-CONVENTION
  STATUS        current
  DESCRIPTION
        "Source managing licenses"
  SYNTAX    INTEGER
        {
            undefined(0),
            nelock(1),
            server(2),
            factory(3),
            flexible(4)
        }

FspR7LicenseManagementCaps ::= TEXTUAL-CONVENTION
  STATUS        current
  DESCRIPTION
        "Source managing licenses"
  SYNTAX    BITS
        {
            capUndefined(0),
            capNelock(1),
            capServer(2),
            capFactory(3),
            capFlexible(4)
        }

FspR7LicenseServerStatus ::= TEXTUAL-CONVENTION
  STATUS        current
  DESCRIPTION
        "License Server connection status"
  SYNTAX    INTEGER
        {
            undefined(0),
            disconnected(1),
            connected(2),
            roleMismatch(3)
        }

FspR7LicenseType ::= TEXTUAL-CONVENTION
  STATUS        current
  DESCRIPTION
        "License Type"
  SYNTAX    INTEGER
        {
            undefined(0),
            permanent(1),
            feature(2),
            master(3)
        }

FspR7LineCoding ::= TEXTUAL-CONVENTION
  STATUS        current
  DESCRIPTION
        "Line Coding"
  SYNTAX    INTEGER
        {
            undefined(0),
            ookNrz(1),
            dpsk(2),
            qpsk(3),
            dpQpsk(4),
            odbPsbt(5),
            mQam(6),
            ofdm(7),
            notDefined(99)
        }

FspR7LineCodingCaps ::= TEXTUAL-CONVENTION
  STATUS        current
  DESCRIPTION
        "Line Coding"
  SYNTAX    BITS
        {
            capUndefined(0),
            capOokNrz(1),
            capDpsk(2),
            capQpsk(3),
            capDpQpsk(4),
            capOdbPsbt(5),
            capMQam(6),
            capOfdm(7),
            capNotDefined(99)
        }

FspR7LLDPChassisType ::= TEXTUAL-CONVENTION
  STATUS        current
  DESCRIPTION
        "LLDP Chassis Type; read from agent on module"
  SYNTAX    INTEGER
        {
            undefined(0),
            chassisComponent(1),
            interfaceAlias(2),
            portComponent(3),
            macAddress(4),
            networkAddress(5),
            interfaceName(6),
            locallyAssigned(7)
        }

FspR7LLDPLocation ::= TEXTUAL-CONVENTION
  STATUS        current
  DESCRIPTION
        "LLDP Interface Location"
  SYNTAX    INTEGER
        {
            undefined(0),
            nearEndRx(1),
            farEndRx(2)
        }

FspR7LLDPManagementInterface ::= TEXTUAL-CONVENTION
  STATUS        current
  DESCRIPTION
        "LLDP Interface type; read from agent on module"
  SYNTAX    INTEGER
        {
            undefined(0),
            unknown(1),
            ifIndex(2),
            systemPortNumber(3)
        }

FspR7LLDPManagementType ::= TEXTUAL-CONVENTION
  STATUS        current
  DESCRIPTION
        "LLDP Management type; read from agent on module"
  SYNTAX    INTEGER
        {
            undefined(0),
            ipv4(1),
            ipv6(2),
            nsap(3),
            mac(4)
        }

FspR7LLDPNeighbors ::= TEXTUAL-CONVENTION
  STATUS        current
  DESCRIPTION
        "LLDP Neighbors in Tx Direction"
  SYNTAX    INTEGER
        {
            undefined(0),
            disable(1),
            no1(2),
            no2(3),
            no3(4),
            no4(5)
        }

FspR7LLDPNeighborsCaps ::= TEXTUAL-CONVENTION
  STATUS        current
  DESCRIPTION
        "LLDP Neighbors in Tx Direction"
  SYNTAX    BITS
        {
            capUndefined(0),
            capDisable(1),
            capNo1(2),
            capNo2(3),
            capNo3(4),
            capNo4(5)
        }

FspR7LLDPPortType ::= TEXTUAL-CONVENTION
  STATUS        current
  DESCRIPTION
        "LLDP Port Type; read from agent on module"
  SYNTAX    INTEGER
        {
            undefined(0),
            interfaceAlias(1),
            portComponent(2),
            macAddress(3),
            networkAddress(4),
            interfaceName(5),
            agentCircuitID(6),
            locallyAssigned(7)
        }

FspR7LLDPScope ::= TEXTUAL-CONVENTION
  STATUS        current
  DESCRIPTION
        "Scope of LLDP propogation based on standard group MAC Addresses"
  SYNTAX    INTEGER
        {
            undefined(0),
            nearestBridge(1), --Nearest Bridge MAC Address
            nearestTPMR(2), --Nearest non-TPMR (Two Port MAC Relay) Bridge
            nearestCustomerBridge(3), --Nearest Customer MAC Address
            nearestBridgeOrTpmr(4), --Both Nearest Bridge and non-TPMR Bridge
            nearestAndCustomer(5), --Nearest Bridge and Customer Bridge
            all(6) --All three MAC add
        }

FspR7LLDPScopeCaps ::= TEXTUAL-CONVENTION
  STATUS        current
  DESCRIPTION
        "Scope of LLDP propogation based on standard group MAC Addresses"
  SYNTAX    BITS
        {
            capUndefined(0),
            capNearestBridge(1),
            capNearestTPMR(2),
            capNearestCustomerBridge(3),
            capNearestBridgeOrTpmr(4),
            capNearestAndCustomer(5),
            capAll(6)
        }

FspR7NoYes ::= TEXTUAL-CONVENTION
  STATUS        current
  DESCRIPTION
        "NoYes variable."
  SYNTAX    INTEGER
        {
            undefined(0),
            no(1),
            yes(2)
        }

FspR7NoYesCaps ::= TEXTUAL-CONVENTION
  STATUS        current
  DESCRIPTION
        "NoYes variable."
  SYNTAX    BITS
        {
            capUndefined(0),
            capNo(1),
            capYes(2)
        }

FspR7ManualAuto ::= TEXTUAL-CONVENTION
  STATUS        current
  DESCRIPTION
        "Manual/Automatic variable."
  SYNTAX    INTEGER
        {
            undefined(0),
            manual(1),
            automatic(2)
        }

FspR7ManualAutoCaps ::= TEXTUAL-CONVENTION
  STATUS        current
  DESCRIPTION
        "Manual/Automatic variable."
  SYNTAX    BITS
        {
            capUndefined(0),
            capManual(1),
            capAutomatic(2)
        }

FspR7MaxBitErrorRate ::= TEXTUAL-CONVENTION
  STATUS        current
  DESCRIPTION
        "Maximum Bit Error Rate"
  SYNTAX    INTEGER
        {
            undefined(0),
            ber1e2(1),
            ber1e3(2),
            ber1e4(3),
            ber1e5(4),
            ber1e6(5),
            ber1e7(6),
            ber1e8(7),
            ber1e9(8),
            ber1e10(9),
            ber1e11(10),
            ber1e12(11),
            ber1e13(12),
            ber1e14(13),
            ber1e15(14)
        }

FspR7MaxBitErrorRateCaps ::= TEXTUAL-CONVENTION
  STATUS        current
  DESCRIPTION
        "Maximum Bit Error Rate"
  SYNTAX    BITS
        {
            capUndefined(0),
            capBer1e2(1),
            capBer1e3(2),
            capBer1e4(3),
            capBer1e5(4),
            capBer1e6(5),
            capBer1e7(6),
            capBer1e8(7),
            capBer1e9(8),
            capBer1e10(9),
            capBer1e11(10),
            capBer1e12(11),
            capBer1e13(12),
            capBer1e14(13),
            capBer1e15(14)
        }

FspR7Mapping ::= TEXTUAL-CONVENTION
  STATUS        current
  DESCRIPTION
        "Type of mapping; transparent or framing"
  SYNTAX    INTEGER
        {
            undefined(0),
            frame(1),
            trans(2)
        }

FspR7MappingCaps ::= TEXTUAL-CONVENTION
  STATUS        current
  DESCRIPTION
        "Type of mapping; transparent or framing"
  SYNTAX    BITS
        {
            capUndefined(0),
            capFrame(1),
            capTrans(2)
        }

FspR7MetroMode ::= TEXTUAL-CONVENTION
  STATUS        current
  DESCRIPTION
        "Operational mode for G.Metro plugs"
  SYNTAX    INTEGER
        {
            undefined(0),
            disabled(1),
            heControlTe(2),
            dfw(3),
            sfw(4)
        }

FspR7MetroModeCaps ::= TEXTUAL-CONVENTION
  STATUS        current
  DESCRIPTION
        "Operational mode for G.Metro plugs"
  SYNTAX    BITS
        {
            capUndefined(0),
            capDisabled(1),
            capHeControlTe(2),
            capDfw(3),
            capSfw(4)
        }

FspR7ModuleNetworkFec ::= TEXTUAL-CONVENTION
  STATUS        current
  DESCRIPTION
        "Sets Forward Error Correction (FEC) for all network ports on the module"
  SYNTAX    INTEGER
        {
            undefined(0),
            gFec(1), --ITU-T G.709, Interleaved RS(255,239), 7% overhead
            eFec2(2) -- ITU-T G.975.1 clause I.4, Interleaved RS(1023,1007)/BCH(2047,1952) Super FEC, 7% overhead
        }

FspR7ModuleNetworkFecCaps ::= TEXTUAL-CONVENTION
  STATUS        current
  DESCRIPTION
        "Sets Forward Error Correction (FEC) for all network ports on the module"
  SYNTAX    BITS
        {
            capUndefined(0),
            capGFec(1),
            capEFec2(2)
        }

FspR7MonLevel ::= TEXTUAL-CONVENTION
  STATUS        current
  DESCRIPTION
        "Highest signal level of intrusive or non-intrusive monitoring. Hardware may monitor the signal one layer higher than Termination Level (TERM)."
  SYNTAX    INTEGER
        {
            undefined(0),
            phys(1),
            otnOtu(2),
            otnOdu(3),
            otnOpu(4),
            sonetSection(5),
            sonetLine(6),
            sonetPath(7),
            pcs(8),
            hoOdu(9)
        }

FspR7MonLevelCaps ::= TEXTUAL-CONVENTION
  STATUS        current
  DESCRIPTION
        "Highest signal level of intrusive or non-intrusive monitoring. Hardware may monitor the signal one layer higher than Termination Level (TERM)."
  SYNTAX    BITS
        {
            capUndefined(0),
            capPhys(1),
            capOtnOtu(2),
            capOtnOdu(3),
            capOtnOpu(4),
            capSonetSection(5),
            capSonetLine(6),
            capSonetPath(7),
            capPcs(8),
            capHoOdu(9)
        }

FspR7MpState ::= TEXTUAL-CONVENTION
  STATUS        current
  DESCRIPTION
        "Master Profile State."
  SYNTAX    INTEGER
        {
            undefined(0),
            empty(1),
            deactivated(2),
            activated(3)
        }

FspR7MpTag ::= TEXTUAL-CONVENTION
  STATUS        current
  DESCRIPTION
        "Master Profile Tag."
  SYNTAX    INTEGER
        {
            undefined(0),
            local(1),
            network(2)
        }

FspR7MuxMethod ::= TEXTUAL-CONVENTION
  STATUS        current
  DESCRIPTION
        "Selection of mux method"
  SYNTAX    INTEGER
        {
            undefined(0),
            sdhSonet(1),
            otn(2)
        }

FspR7MuxMethodCaps ::= TEXTUAL-CONVENTION
  STATUS        current
  DESCRIPTION
        "Selection of mux method"
  SYNTAX    BITS
        {
            capUndefined(0),
            capSdhSonet(1),
            capOtn(2)
        }

FspR7NaasMode ::= TEXTUAL-CONVENTION
  STATUS        current
  DESCRIPTION
        "Defines node attributes advertisement mode."
  SYNTAX    INTEGER
        {
            undefined(0),
            allTlv(1), --LSA type 11 includes old and new TLVs
            newTlv(2), --LSA type 11 includes new TLVs per standard
            advertiseBlock(3) --LSA type 11 does not include TLV advertisement
        }

FspR7NCTraceId ::= TEXTUAL-CONVENTION
  STATUS        current
  DESCRIPTION
        "Node Channel Trace ID - It associates each direction of a channel trace through a node."
  SYNTAX    INTEGER
        {
            undefined(0),
            id1(1),
            id2(2),
            id3(3),
            id4(4),
            id5(5),
            id6(6),
            id7(7),
            id8(8),
            id9(9),
            id10(10),
            id11(11),
            id12(12),
            id13(13),
            id14(14),
            id15(15),
            id16(16),
            id17(17),
            id18(18),
            id19(19),
            id20(20),
            id21(21),
            id22(22),
            id23(23),
            id24(24),
            id25(25),
            id26(26),
            id27(27),
            id28(28)
        }

FspR7NCTRouteType ::= TEXTUAL-CONVENTION
  STATUS        current
  DESCRIPTION
        "ROUTE-TYPE = NONE | FIBER | CABLE | BKPLANE | EQPT | PROVND.  ROUTE-TYPE
        parameter indicates the connection type between two ports. If a connection
        between the two ports is within a module (i.e. Client to Network port),
        the Route-Type is either provisioned (PROVND) of fixed (EQPT). If the connection
        is between two modules' ports; then the Route-Type is FIBER, or CABLE, or BKPLANE."
  SYNTAX    INTEGER
        {
            undefined(0),
            none(1), --No connection between ports
            fiber(2), --Connection between ports is a fiber optic cable
            cable(3), --Connection between ports is an electrical cable
            backPlane(4), --Connection between ports or modules is through Backplane
            equipment(5), --Connection between ports on the same module cannot be changed (not affected by provisioning).
            provisioned(6) --Connection between ports on the same module is determined by provisional parameter(s) (mode, channel, cross-connect, etc.)
        }

FspR7NIAdvertMode ::= TEXTUAL-CONVENTION
  STATUS        current
  DESCRIPTION
        "Network Intelligence Resource Advertisement Mode"
  SYNTAX    INTEGER
        {
            undefined(0),
            te(1),
            mla(2)
        }

FspR7NtpAuthType ::= TEXTUAL-CONVENTION
  STATUS        current
  DESCRIPTION
        "Type of NTP authentication."
  SYNTAX    INTEGER
        {
            undefined(0),
            none(1),
            privateKey(2)
        }

FspR7NtpSyncStatus ::= TEXTUAL-CONVENTION
  STATUS        current
  DESCRIPTION
        "NTP Synchronization Status"
  SYNTAX    INTEGER
        {
            undefined(0),
            noData(1),
            systemPeer(2),
            falseTicker(3),
            candidate(4),
            discarded(5),
            inProgress(6),
            notApplicable(7)
        }

FspR7NtpTestStatus ::= TEXTUAL-CONVENTION
  STATUS        current
  DESCRIPTION
        "NTP Server Test Status"
  SYNTAX    INTEGER
        {
            undefined(0),
            success(1),
            fail(2),
            idle(3),
            inProgress(4)
        }

FspR7NumberOfChannels ::= TEXTUAL-CONVENTION
  STATUS        current
  DESCRIPTION
        "Number of channels supported by an entity"
  SYNTAX    INTEGER
        {
            undefined(0),
            channels20(1),
            channels40(2),
            channels80(3),
            channels96(4),
            channels8(5),
            channels192(7),
            channels128(8),
            channels48(9),
            channels64(11),
            channels16(10),
            notDefined(6)
        }

FspR7NumberOfChannelsCaps ::= TEXTUAL-CONVENTION
  STATUS        current
  DESCRIPTION
        "Number of channels supported by an entity"
  SYNTAX    BITS
        {
            capUndefined(0),
            capChannels20(1),
            capChannels40(2),
            capChannels80(3),
            capChannels96(4),
            capChannels8(5),
            capChannels192(7),
            capChannels128(8),
            capChannels48(9),
            capChannels64(11),
            capChannels16(10),
            capNotDefined(6)
        }

FspR7OdtuType ::= TEXTUAL-CONVENTION
  STATUS        current
  DESCRIPTION
        "ODTU Transport Unit"
  SYNTAX    INTEGER
        {
            undefined(0),
            odtu01(1),
            odtu12(2),
            odtu2dsh1(3),
            odtu2dshTS(4),
            odtu13(5),
            odtu23(6),
            odtu3dsh1(7),
            odtu3dsh9(8),
            odtu3dshTS(9),
            odtu4dsh1(10),
            odtu4dsh2(11),
            odtu4dsh8(12),
            odtu4dsh31(13),
            odtu4dshTS(14),
            odtuCndsh1(15),
            odtuCndsh2(16),
            odtuCndsh20(17),
            odtuCndshTS(18)
        }

FspR7OduMultiplexStructure ::= TEXTUAL-CONVENTION
  STATUS        current
  DESCRIPTION
        "ODU Multiplex Structure. The possible values depend on the high order ODUk: ODUCn=22; ODU4=21;  ODU3=(21,20); ODU2=(21,20); ODU1=20."
  SYNTAX    INTEGER
        {
            undefined(0),
            ptOduMux20(1), --ODU multiplex structure supporting ODTUjk only, (AMP only).
            ptOduMux21(2), --ODU multiplex structure supporting ODTUk.ts or ODTUk.ts and ODTUjk, (GMP capable)
            ptOduMux22(3), --ODU multiplex structure supporting ODTUCn.ts, (GMP capable)
            ptOduMuxNotDefined(499)
        }

FspR7OduMultiplexStructureCaps ::= TEXTUAL-CONVENTION
  STATUS        current
  DESCRIPTION
        "ODU Multiplex Structure. The possible values depend on the high order ODUk: ODUCn=22; ODU4=21;  ODU3=(21,20); ODU2=(21,20); ODU1=20."
  SYNTAX    BITS
        {
            capUndefined(0),
            capPtOduMux20(1),
            capPtOduMux21(2),
            capPtOduMux22(3),
            capPtOduMuxNotDefined(499)
        }

FspR7OperState ::= TEXTUAL-CONVENTION
  STATUS        current
  DESCRIPTION
        "The Operational State will be displayed on the
        GUI with full name values;  it will be differently
        displayed in TL1 syntax according to TL1 display rules."
  SYNTAX    INTEGER
        {
            undefined(0),
            nr(1),
            anr(2),
            out(3),
            un(4)
        }

FspR7OpticalBand ::= TEXTUAL-CONVENTION
  STATUS        current
  DESCRIPTION
        "OM Band - Inventory. BAND__PROVISION references to this."
  SYNTAX    INTEGER
        {
            undefined(0),
            bandC(1),
            bandL(2),
            bandA(3),
            bandB(4),
            -- bandAny(5),
            bandCi(5),
            bandCandCi(6)
        }

FspR7OpticalBandCaps ::= TEXTUAL-CONVENTION
  STATUS        current
  DESCRIPTION
        "OM Band - Inventory. BAND__PROVISION references to this."
  SYNTAX    BITS
        {
            capUndefined(0),
            capBandC(1),
            capBandL(2),
            capBandA(3),
            capBandB(4),
            -- capBandAny(5),
            capBandCi(5),
            capBandCandCi(6)
        }

FspR7OpticalFiberType ::= TEXTUAL-CONVENTION
  STATUS        current
  DESCRIPTION
        "Fiber of Optical Interface - Inventory. FIBER references to this."
  SYNTAX    INTEGER
        {
            undefined(0),
            singleMode(1),
            multiMode(2),
            any(3)
        }

FspR7OpticalFiberTypeCaps ::= TEXTUAL-CONVENTION
  STATUS        current
  DESCRIPTION
        "Fiber of Optical Interface - Inventory. FIBER references to this."
  SYNTAX    BITS
        {
            capUndefined(0),
            capSingleMode(1),
            capMultiMode(2),
            capAny(3)
        }

FspR7OpticalGroup ::= TEXTUAL-CONVENTION
  STATUS        current
  DESCRIPTION
        "Channel Group read from the hardware"
  SYNTAX    INTEGER
        {
            undefined(0),
            d01d04(1),
            d05d08(2),
            d09d12(3),
            d13d16(4),
            d17d20(5),
            d21d24(6),
            d25d28(7),
            d29d32(8),
            d33d36(9),
            d37d40(10),
            d41d44(11),
            d45d48(12),
            d49d52(13),
            d53d56(14),
            d57d60(15),
            d61d64(16),
            -- any(17),
            f19590f19560(17),
            f19550f19520(18),
            f19510f19480(19),
            f19470f19440(20),
            f19430f19400(21),
            f19390f19360(22),
            f19350f19320(23),
            f19310f19280(24),
            f19270f19240(25),
            f19230f19200(26),
            f19590f19520(27), --D02-D04, DC1, D05-D08
            f19510f19440(28), --DC2, D09-D12, DC3, D13-D14
            f19430f19360(29), --D15-D16, DC4, DC9, D17-D19
            f19350f19280(30), --D2, DC6, D21-D24, DC7, D25
            f19270f19200(31), --D26-D28, DC8, D29-D32
            f19590f19500(32),
            f19350f19260(34),
            f19430f19290(35), --low loss 200GHz grid for Juniper
            f19610f19450(36)
        }

FspR7OpticalGroupCaps ::= TEXTUAL-CONVENTION
  STATUS        current
  DESCRIPTION
        "Channel Group read from the hardware"
  SYNTAX    BITS
        {
            capUndefined(0),
            capD01d04(1),
            capD05d08(2),
            capD09d12(3),
            capD13d16(4),
            capD17d20(5),
            capD21d24(6),
            capD25d28(7),
            capD29d32(8),
            capD33d36(9),
            capD37d40(10),
            capD41d44(11),
            capD45d48(12),
            capD49d52(13),
            capD53d56(14),
            capD57d60(15),
            capD61d64(16),
            -- capAny(17),
            capF19590f19560(17),
            capF19550f19520(18),
            capF19510f19480(19),
            capF19470f19440(20),
            capF19430f19400(21),
            capF19390f19360(22),
            capF19350f19320(23),
            capF19310f19280(24),
            capF19270f19240(25),
            capF19230f19200(26),
            capF19590f19520(27),
            capF19510f19440(28),
            capF19430f19360(29),
            capF19350f19280(30),
            capF19270f19200(31),
            capF19590f19500(32),
            capF19350f19260(34),
            capF19430f19290(35),
            capF19610f19450(36)
        }

FspR7OpticalInterfaceReach ::= TEXTUAL-CONVENTION
  STATUS        current
  DESCRIPTION
        "Reach"
  SYNTAX    INTEGER
        {
            undefined(0),
            intra(1), --0.5 - <5 km;  850nm;  MM fiber
            short(2), --5 - <30 km;  1310nm;  SM fiber
            long(4), --30 - <70 km;  1550nm;  SM fiber
            vlong(5), --70 - <110 km;  15xx;  SM fiber
            ulong(6), --110 - <165 km;  SM fiber
            reg(7), --290 - <360 km;  SM fiber
            xlong(8), --360 - <600 km;  SM fiber
            -- deprecated(9),
            longn(10), --30 - <70 km;  15xx;  SM fiber
            extended(11), --165 - <220 km;  SM fiber
            hyperlong(12), --220 - <290 km;  SM fiber
            longNR(13), --30 - <70 km; 15xx;  SM fiber
            ulongHaul(14), --500 - <2500 km 
            shortIntra(15), --0 - <500 m;  850nm;  MM fiber
            ulongHaulC(16), --500 - <2500 km 
            longR(17), --20-40 km; 1550nm; SM fiber
            vlongX(18), --85 - <125 km;  1550nm;  SM fiber
            vshort(19), --0 - <5 km; 1310nm; SM fiber
            any(20)
        }

FspR7OpticalInterfaceReachCaps ::= TEXTUAL-CONVENTION
  STATUS        current
  DESCRIPTION
        "Reach"
  SYNTAX    BITS
        {
            capUndefined(0),
            capIntra(1),
            capShort(2),
            capLong(4),
            capVlong(5),
            capUlong(6),
            capReg(7),
            capXlong(8),
            -- capDeprecated(9),
            capLongn(10),
            capExtended(11),
            capHyperlong(12),
            capLongNR(13),
            capUlongHaul(14),
            capShortIntra(15),
            capUlongHaulC(16),
            capLongR(17),
            capVlongX(18),
            capVshort(19),
            capAny(20)
        }

FspR7OpticalLanes ::= TEXTUAL-CONVENTION
  STATUS        current
  DESCRIPTION
        "Number of Optical Transport Lanes in OTLG"
  SYNTAX    INTEGER
        {
            undefined(0),
            lanesNumber4(1),
            lanesNumber2(2)
        }

FspR7OpticalMultiplexLevel ::= TEXTUAL-CONVENTION
  STATUS        current
  DESCRIPTION
        "Optical Multiplex Level"
  SYNTAX    INTEGER
        {
            undefined(0),
            levelOm1D(1),
            levelOm1C(2),
            levelOm4D(3),
            levelOm4C(4),
            levelOm16D(5),
            levelOm32D(6),
            levelOm40D(7),
            levelOmC(9),
            levelOmD(10),
            levelOtD(11),
            levelOtC(12),
            levelOt(13),
            levelOm8D(14)
        }

FspR7OpticalSubBand ::= TEXTUAL-CONVENTION
  STATUS        current
  DESCRIPTION
        "Subband - Inventory"
  SYNTAX    INTEGER
        {
            undefined(0),
            d01d16(1),
            d17d32(2),
            d33d48(3),
            d49d64(4) 
            -- subBandAny(5)
        }

FspR7OpticalSubBandCaps ::= TEXTUAL-CONVENTION
  STATUS        current
  DESCRIPTION
        "Subband - Inventory"
  SYNTAX    BITS
        {
            capUndefined(0),
            capD01d16(1),
            capD17d32(2),
            capD33d48(3),
            capD49d64(4) 
            -- capSubBandAny(5)
        }

FspR7OpuPayloadType ::= TEXTUAL-CONVENTION
  STATUS        current
  DESCRIPTION
        "OPU Payload Type Indicator"
  SYNTAX    INTEGER
        {
            undefined(0),
            pt01(1), --Experimental mapping
            pt02(2), --Asynchronous CBR mapping
            pt03(3), --Bit synchronous CBR mapping
            pt04(4), --ATM mapping
            pt05(5), --GFP mapping
            pt06(6), --Virtual Concatenated signal
            pt07(7), --1000Base-X into ODU0 OR 40Gbase-R into OPU3 OR 100GBase-R into OPU4 mapping
            pt08(8), --FC-1200 into ODU2e mapping
            pt09(9), --GFP mapping into Extended OPU2 payload
            pt0A(10), --STM-1 mapping into ODU0
            pt0B(11), --STM-4 mapping into ODU0
            pt0C(12), --FC-100 mapping into ODU0
            pt0D(13), --FC-200 mapping into ODU1
            pt0E(14), --FC-400 mapping into ODUflex
            pt0F(15), --FC-800 mapping into ODUflex
            pt10(16), --Bit stream with octet timing mapping
            pt11(17), --Bit stream without octet timing mapping
            pt20(18), --ODU multiplex structure supporting ODTUjk only, (AMP only)
            pt21(19), --ODU multiplex structure supporting ODTUk.ts or ODTUk.ts and ODTUjk, (GMP capable)
            pt80(20), --Reserved codes for proprietary use
            pt81(21), --Reserved codes for proprietary use
            pt82(22), --Reserved codes for proprietary use
            pt83(23), --Reserved codes for proprietary use
            pt84(24), --Reserved codes for proprietary use
            pt85(25), --Reserved codes for proprietary use
            pt86(26), --Reserved codes for proprietary use
            pt87(27), --Reserved codes for proprietary use
            pt88(28), --Reserved codes for proprietary use
            pt89(29), --Reserved codes for proprietary use
            pt8A(30), --Reserved codes for proprietary use
            pt8B(31), --Reserved codes for proprietary use
            pt8C(32), --Reserved codes for proprietary use
            pt8D(33), --Reserved codes for proprietary use
            pt8E(34), --Reserved codes for proprietary use
            pt8F(35), --Reserved codes for proprietary use
            ptFD(36), --NULL test signal mapping
            ptFE(37), --PRBS test signal mapping
            pt8X(38),
            pt1F(39),
            pt30(40),
            pt1C(41),
            ptNotDefined(499)
        }

FspR7OpuPayloadTypeCaps ::= TEXTUAL-CONVENTION
  STATUS        current
  DESCRIPTION
        "OPU Payload Type Indicator"
  SYNTAX    BITS
        {
            capUndefined(0),
            capPt01(1),
            capPt02(2),
            capPt03(3),
            capPt04(4),
            capPt05(5),
            capPt06(6),
            capPt07(7),
            capPt08(8),
            capPt09(9),
            capPt0A(10),
            capPt0B(11),
            capPt0C(12),
            capPt0D(13),
            capPt0E(14),
            capPt0F(15),
            capPt10(16),
            capPt11(17),
            capPt20(18),
            capPt21(19),
            capPt80(20),
            capPt81(21),
            capPt82(22),
            capPt83(23),
            capPt84(24),
            capPt85(25),
            capPt86(26),
            capPt87(27),
            capPt88(28),
            capPt89(29),
            capPt8A(30),
            capPt8B(31),
            capPt8C(32),
            capPt8D(33),
            capPt8E(34),
            capPt8F(35),
            capPtFD(36),
            capPtFE(37),
            capPt8X(38),
            capPt1F(39),
            capPt30(40),
            capPt1C(41),
            capPtNotDefined(499)
        }

FspR7Optimize ::= TEXTUAL-CONVENTION
  STATUS        current
  DESCRIPTION
        "Optimizes port for either protection switch time or traffic regeneration operation"
  SYNTAX    INTEGER
        {
            undefined(0),
            regen(1),
            protect(2)
        }

FspR7OptimizeCaps ::= TEXTUAL-CONVENTION
  STATUS        current
  DESCRIPTION
        "Optimizes port for either protection switch time or traffic regeneration operation"
  SYNTAX    BITS
        {
            capUndefined(0),
            capRegen(1),
            capProtect(2)
        }

FspR7OscChannel ::= TEXTUAL-CONVENTION
  STATUS        current
  DESCRIPTION
        "OSC Channel"
  SYNTAX    INTEGER
        {
            undefined(0),
            s1310(99), --1310,00nm OSC
            s1630(100), --1630,00nm OSC
            s1510(106), --1510,00nm OSC
            s1610(197), --1610,00nm OSC
            s1490(199), --1490,00nm OSC
            f19610(107), --196,10THz  1528,7734nm
            notDefined(500)
        }

FspR7OscChannelCaps ::= TEXTUAL-CONVENTION
  STATUS        current
  DESCRIPTION
        "OSC Channel"
  SYNTAX    BITS
        {
            capUndefined(0),
            capS1310(99),
            capS1630(100),
            capS1510(106),
            capS1610(197),
            capS1490(199),
            capF19610(107),
            capNotDefined(500)
        }

FspR7OscUsage ::= TEXTUAL-CONVENTION
  STATUS        current
  DESCRIPTION
        "Select if and how the OSC is to be used on an amplifier"
  SYNTAX    INTEGER
        {
            undefined(0),
            none(1), --No OSC usage
            osctxctrl(2), --Use the OSC Tx Control
            oscrx(3), --Use the OSC Rx
            osctxandrx(4) --Use OSC Tx and Rx
        }

FspR7OscUsageCaps ::= TEXTUAL-CONVENTION
  STATUS        current
  DESCRIPTION
        "Select if and how the OSC is to be used on an amplifier"
  SYNTAX    BITS
        {
            capUndefined(0),
            capNone(1),
            capOsctxctrl(2),
            capOscrx(3),
            capOsctxandrx(4)
        }

FspR7OspfMode ::= TEXTUAL-CONVENTION
  STATUS        current
  DESCRIPTION
        "OSPF Routing (Dynamic)"
  SYNTAX    INTEGER
        {
            undefined(0),
            enable(1),
            disable(2),
            passive(3)
        }

FspR7OspfModeCaps ::= TEXTUAL-CONVENTION
  STATUS        current
  DESCRIPTION
        "OSPF Routing (Dynamic)"
  SYNTAX    BITS
        {
            capUndefined(0),
            capEnable(1),
            capDisable(2),
            capPassive(3)
        }

FspR7OtdrPeriod ::= TEXTUAL-CONVENTION
  STATUS        current
  DESCRIPTION
        "NONE - OTDR measurement disabled otherwise the OTDR duration in minutes."
  SYNTAX    INTEGER
        {
            undefined(0),
            periodNone(1),
            period5ms(2),
            period20ms(3),
            period40ms(4),
            period60ms(5)
        }

FspR7OtdrPeriodCaps ::= TEXTUAL-CONVENTION
  STATUS        current
  DESCRIPTION
        "NONE - OTDR measurement disabled otherwise the OTDR duration in minutes."
  SYNTAX    BITS
        {
            capUndefined(0),
            capPeriodNone(1),
            capPeriod5ms(2),
            capPeriod20ms(3),
            capPeriod40ms(4),
            capPeriod60ms(5)
        }

FspR7ParityBit ::= TEXTUAL-CONVENTION
  STATUS        current
  DESCRIPTION
        "Parity Bit Settings"
  SYNTAX    INTEGER
        {
            undefined(0),
            no(1)
        }

FspR7ParityBitCaps ::= TEXTUAL-CONVENTION
  STATUS        current
  DESCRIPTION
        "Parity Bit Settings"
  SYNTAX    BITS
        {
            capUndefined(0),
            capNo(1)
        }

FspR7PasswordHashType ::= TEXTUAL-CONVENTION
  STATUS        current
  DESCRIPTION
        "Type of algorithm used to hash the user password"
  SYNTAX    INTEGER
        {
            undefined(0),
            md5(1),
            sha(2),
            sha256(5),
            sha512(6),
            other(15)
        }

FspR7PathNode ::= TEXTUAL-CONVENTION
  STATUS        current
  DESCRIPTION
        "Node count along a signal path on a unidirectional basis from the client signal ingress to egress"
  SYNTAX    INTEGER
        {
            undefined(0),
            node1(1),
            node2(2),
            node3(3),
            node4(4),
            node5(5),
            node6(6),
            node7(7),
            node8(8),
            node9(9),
            node10(10),
            node11(11),
            node12(12),
            node13(13),
            node14(14),
            node15(15),
            node16(16),
            node17(17),
            node18(18),
            node19(19),
            node20(20),
            node21(21),
            node22(22),
            node23(23),
            node24(24),
            node25(25),
            node26(26),
            node27(27),
            node28(28),
            node29(29),
            node30(30),
            node31(31),
            node32(32),
            node33(33),
            node34(34),
            node35(35),
            node36(36),
            node37(37),
            node38(38),
            node39(39),
            node40(40),
            node41(41),
            node42(42),
            node43(43),
            node44(44),
            node45(45),
            node46(46),
            node47(47),
            node48(48),
            node49(49),
            node50(50),
            node51(51),
            node52(52),
            node53(53),
            node54(54),
            node55(55),
            node56(56),
            node57(57),
            node58(58),
            node59(59),
            node60(60),
            node61(61),
            node62(62),
            node63(63),
            node64(64),
            node65(65),
            node66(66),
            node67(67),
            node68(68),
            node69(69),
            node70(70),
            node71(71),
            node72(72),
            node73(73),
            node74(74),
            node75(75),
            node76(76),
            node77(77),
            node78(78),
            node79(79),
            node80(80),
            node81(81),
            node82(82),
            node83(83),
            node84(84),
            node85(85),
            node86(86),
            node87(87),
            node88(88),
            node89(89),
            node90(90),
            node91(91),
            node92(92),
            node93(93),
            node94(94),
            node95(95),
            node96(96),
            node97(97),
            node98(98),
            node99(99),
            node100(100),
            node101(101),
            node102(102),
            node103(103),
            node104(104),
            node105(105),
            node106(106),
            node107(107),
            node108(108),
            node109(109),
            node110(110),
            node111(111),
            node112(112),
            node113(113),
            node114(114),
            node115(115),
            node116(116),
            node117(117),
            node118(118),
            notDefined(499)
        }

FspR7PathNodeCaps ::= TEXTUAL-CONVENTION
  STATUS        current
  DESCRIPTION
        "Node count along a signal path on a unidirectional basis from the client signal ingress to egress"
  SYNTAX    BITS
        {
            capUndefined(0),
            capNode1(1),
            capNode2(2),
            capNode3(3),
            capNode4(4),
            capNode5(5),
            capNode6(6),
            capNode7(7),
            capNode8(8),
            capNode9(9),
            capNode10(10),
            capNode11(11),
            capNode12(12),
            capNode13(13),
            capNode14(14),
            capNode15(15),
            capNode16(16),
            capNode17(17),
            capNode18(18),
            capNode19(19),
            capNode20(20),
            capNode21(21),
            capNode22(22),
            capNode23(23),
            capNode24(24),
            capNode25(25),
            capNode26(26),
            capNode27(27),
            capNode28(28),
            capNode29(29),
            capNode30(30),
            capNode31(31),
            capNode32(32),
            capNode33(33),
            capNode34(34),
            capNode35(35),
            capNode36(36),
            capNode37(37),
            capNode38(38),
            capNode39(39),
            capNode40(40),
            capNode41(41),
            capNode42(42),
            capNode43(43),
            capNode44(44),
            capNode45(45),
            capNode46(46),
            capNode47(47),
            capNode48(48),
            capNode49(49),
            capNode50(50),
            capNode51(51),
            capNode52(52),
            capNode53(53),
            capNode54(54),
            capNode55(55),
            capNode56(56),
            capNode57(57),
            capNode58(58),
            capNode59(59),
            capNode60(60),
            capNode61(61),
            capNode62(62),
            capNode63(63),
            capNode64(64),
            capNode65(65),
            capNode66(66),
            capNode67(67),
            capNode68(68),
            capNode69(69),
            capNode70(70),
            capNode71(71),
            capNode72(72),
            capNode73(73),
            capNode74(74),
            capNode75(75),
            capNode76(76),
            capNode77(77),
            capNode78(78),
            capNode79(79),
            capNode80(80),
            capNode81(81),
            capNode82(82),
            capNode83(83),
            capNode84(84),
            capNode85(85),
            capNode86(86),
            capNode87(87),
            capNode88(88),
            capNode89(89),
            capNode90(90),
            capNode91(91),
            capNode92(92),
            capNode93(93),
            capNode94(94),
            capNode95(95),
            capNode96(96),
            capNode97(97),
            capNode98(98),
            capNode99(99),
            capNode100(100),
            capNode101(101),
            capNode102(102),
            capNode103(103),
            capNode104(104),
            capNode105(105),
            capNode106(106),
            capNode107(107),
            capNode108(108),
            capNode109(109),
            capNode110(110),
            capNode111(111),
            capNode112(112),
            capNode113(113),
            capNode114(114),
            capNode115(115),
            capNode116(116),
            capNode117(117),
            capNode118(118),
            capNotDefined(499)
        }

FspR7PathProt ::= TEXTUAL-CONVENTION
  STATUS        current
  DESCRIPTION
        "Indicates the traffic path for path protection cases when the FFP does not exist.  When the FFP exists, protected is indicated and the status is determined by the FFP."
  SYNTAX    INTEGER
        {
            undefined(0),
            none(1), --no CRS exists
            unprotActive(2), --CRS exist, no FFP exists, traffic is on this path
            unprotIdle(3), --CRS exists, no FFP exist, traffic is not on this path
            protected(4) --CRS exist, FFP exist, the paths are protected and the FFP determines status.
        }

FspR7PlugDataRate ::= TEXTUAL-CONVENTION
  STATUS        current
  DESCRIPTION
        "Rate"
  SYNTAX    INTEGER
        {
            undefined(0),
            rateCouplingLink(1),
            rateHighSpeed(2),
            rateGBe(3),
            rate2G1(4),
            rate2G5(5),
            rate4G(6),
            rate10G(7),
            any(8),
            rate11G(9),
            rateFE(10),
            rate10G2R(11),
            rate8G(12),
            rate103G(13),
            rate112G(14),
            rate16G(15),
            rate3gSdi(16),
            rate3G(17),
            rateMadi(18),
            rate6G(19),
            rate43G(20),
            rate56G(21),
            rate14G(22),
            rate224G(23),
            rate25G(24),
            rate32G(25),
            rate425G(26),
            rate106G(27), --106.25Gbit/s (100GE, Infiniband NDR, PAM4 53.125GBd)
            rate448G(28),
            rate64G(29)
        }

FspR7PlugDataRateCaps ::= TEXTUAL-CONVENTION
  STATUS        current
  DESCRIPTION
        "Rate"
  SYNTAX    BITS
        {
            capUndefined(0),
            capRateCouplingLink(1),
            capRateHighSpeed(2),
            capRateGBe(3),
            capRate2G1(4),
            capRate2G5(5),
            capRate4G(6),
            capRate10G(7),
            capAny(8),
            capRate11G(9),
            capRateFE(10),
            capRate10G2R(11),
            capRate8G(12),
            capRate103G(13),
            capRate112G(14),
            capRate16G(15),
            capRate3gSdi(16),
            capRate3G(17),
            capRateMadi(18),
            capRate6G(19),
            capRate43G(20),
            capRate56G(21),
            capRate14G(22),
            capRate224G(23),
            capRate25G(24),
            capRate32G(25),
            capRate425G(26),
            capRate106G(27),
            capRate448G(28),
            capRate64G(29)
        }

FspR7PlugType ::= TEXTUAL-CONVENTION
  STATUS        current
  DESCRIPTION
        "Plug Type"
  SYNTAX    INTEGER
        {
            undefined(0),
            lr4(1),
            sr4(2),
            psm4(3),
            cwdm4(4),
            er4f(5),
            typ4lr(6),
            cwdm4e(7), --CWDM4 with short range
            sr2bd(8), --Short range, bidirectional
            fr4(9),
            pam4(10),
            dac(11),
            optical(12),
            any(13),
            fr(14),
            lr(15),
            dr(16)
        }

FspR7PlugTypeCaps ::= TEXTUAL-CONVENTION
  STATUS        current
  DESCRIPTION
        "Plug Type"
  SYNTAX    BITS
        {
            capUndefined(0),
            capLr4(1),
            capSr4(2),
            capPsm4(3),
            capCwdm4(4),
            capEr4f(5),
            capTyp4lr(6),
            capCwdm4e(7),
            capSr2bd(8),
            capFr4(9),
            capPam4(10),
            capDac(11),
            capOptical(12),
            capAny(13),
            capFr(14),
            capLr(15),
            capDr(16)
        }

FspR7PlugMode ::= TEXTUAL-CONVENTION
  STATUS        current
  DESCRIPTION
        "Plug Mode"
  SYNTAX    INTEGER
        {
            undefined(0),
            mode10g(1),
            mode40g(2),
            mode100g(3)
        }

FspR7PlugModeCaps ::= TEXTUAL-CONVENTION
  STATUS        current
  DESCRIPTION
        "Plug Mode"
  SYNTAX    BITS
        {
            capUndefined(0),
            capMode10g(1),
            capMode40g(2),
            capMode100g(3)
        }

FspR7PmMode ::= TEXTUAL-CONVENTION
  STATUS        current
  DESCRIPTION
        "Mode of PM counters"
  SYNTAX    INTEGER
        {
            undefined(0),
            enableAll(1),
            enableCurrent(2),
            disable(3)
        }

FspR7PmModeCaps ::= TEXTUAL-CONVENTION
  STATUS        current
  DESCRIPTION
        "Mode of PM counters"
  SYNTAX    BITS
        {
            capUndefined(0),
            capEnableAll(1),
            capEnableCurrent(2),
            capDisable(3)
        }

FspR7PmReset ::= TEXTUAL-CONVENTION
  STATUS        current
  DESCRIPTION
        "Reset data-layer Performance registers"
  SYNTAX    INTEGER
        {
            undefined(0),
            none(1),
            all(2),
            curr(3)
        }

FspR7PmResetCaps ::= TEXTUAL-CONVENTION
  STATUS        current
  DESCRIPTION
        "Reset data-layer Performance registers"
  SYNTAX    BITS
        {
            capUndefined(0),
            capNone(1),
            capAll(2),
            capCurr(3)
        }

FspR7PmSnapshotStatus ::= TEXTUAL-CONVENTION
  STATUS        current
  DESCRIPTION
        "Reference value Status"
  SYNTAX    INTEGER
        {
            undefined(0),
            none(1),
            inProgress(2),
            success(3),
            error(4)
        }

FspR7PmSnapshotParameterTypes ::= TEXTUAL-CONVENTION
  STATUS        current
  DESCRIPTION
        "List of PM Snapshot parameters"
  SYNTAX        INTEGER
                {
                  undefined(0),
               outputPower(1),
               inputPower(2),
               attenuation(3),
               attenuationOfVoa(4),
               oscGain(5),
               backreflectionPowerReceived(6),
               ramanPumpPower(7),
               oscPowerReceived(8),
               variableGain(9),
               txLineAttenuation(10),
               rxLineAttenuation(11),
               totalInputPower(12)
                }

FspR7PolarizationTracking ::= TEXTUAL-CONVENTION
  STATUS        current
  DESCRIPTION
        "State of Polarisation tracking"
  SYNTAX    INTEGER
        {
            undefined(0),
            fast(1),
            normal(2)
        }

FspR7PolarizationTrackingCaps ::= TEXTUAL-CONVENTION
  STATUS        current
  DESCRIPTION
        "State of Polarisation tracking"
  SYNTAX    BITS
        {
            capUndefined(0),
            capFast(1),
            capNormal(2)
        }

FspR7Modulation ::= TEXTUAL-CONVENTION
  STATUS        current
  DESCRIPTION
        "Modulation"
  SYNTAX    INTEGER
        {
            undefined(0),
            modulationDpQpsk(1), --Dual polarization QPSK (Qadrature Phase Shift Keying)
            modulation8qam(2), --Dual polarization 8QAM (Quadrature Amplitude Modulation)
            modulation16qam(3), --Dual polarization 16QAM (Quadrature Amplitude Modulation)
            modulation32qam(4), --Dual polarization 32QAM (Quadrature Amplitude Modulation)
            modulation64qam(5), --Dual polarization 64QAM (Quadrature Amplitude Modulation)
            modulation16pqam(6), --Dual polarization partial set 16QAM
            modulation32n64qam(7), --Dual polarization 32QAM and 64QAM mixed
            modulation16n32qam(8), --Dual polarization 16QAM and 32QAM mixed
            modulation16pn32qam(10), --Dual polarization partial set 16QAM and 32QAM mixed
            modulation16pnQpsk(11), --Dual polarization partial set QPSK and 16QAM mixed
            modulation16pm16qam(12) --Dual polarization partial set 16QAM and 16QAM mixed
        }

FspR7ModulationCaps ::= TEXTUAL-CONVENTION
  STATUS        current
  DESCRIPTION
        "Modulation"
  SYNTAX    BITS
        {
            capUndefined(0),
            capModulationDpQpsk(1),
            capModulation8qam(2),
            capModulation16qam(3),
            capModulation32qam(4),
            capModulation64qam(5),
            capModulation16pqam(6),
            capModulation32n64qam(7),
            capModulation16n32qam(8),
            capModulation16pn32qam(10),
            capModulation16pnQpsk(11),
            capModulation16pm16qam(12)
        }

FspR7PortBehaviour ::= TEXTUAL-CONVENTION
  STATUS        current
  DESCRIPTION
        "Behavior or Port usage based on configuration/usage in the system regardless of faceplate designation"
  SYNTAX    INTEGER
        {
            undefined(0),
            client(1), --Client Interface Side Behavior
            network(2) --Network Interface Side Behavior
        }

FspR7PortBehaviourCaps ::= TEXTUAL-CONVENTION
  STATUS        current
  DESCRIPTION
        "Behavior or Port usage based on configuration/usage in the system regardless of faceplate designation"
  SYNTAX    BITS
        {
            capUndefined(0),
            capClient(1),
            capNetwork(2)
        }

FspR7PortMode ::= TEXTUAL-CONVENTION
  STATUS        current
  DESCRIPTION
        "Port Mode"
  SYNTAX    INTEGER
        {
            undefined(0),
            port(1),
            cTag(2),
            sTag(3)
        }

FspR7PortModeCaps ::= TEXTUAL-CONVENTION
  STATUS        current
  DESCRIPTION
        "Port Mode"
  SYNTAX    BITS
        {
            capUndefined(0),
            capPort(1),
            capCTag(2),
            capSTag(3)
        }

FspR7PortRole ::= TEXTUAL-CONVENTION
  STATUS        current
  DESCRIPTION
        "ADVA cloud Port Roles"
  SYNTAX    INTEGER
        {
            undefined(0),
            uni(1), --User Network Interface
            iNni(2), --ADVA Interconnect Network Network Interface
            nni(3) --Network Network Interface
        }

FspR7PortRoleCaps ::= TEXTUAL-CONVENTION
  STATUS        current
  DESCRIPTION
        "ADVA cloud Port Roles"
  SYNTAX    BITS
        {
            capUndefined(0),
            capUni(1),
            capINni(2),
            capNni(3)
        }

FspR7PrivacyKeyType ::= TEXTUAL-CONVENTION
  STATUS        current
  DESCRIPTION
        "Defines if SNMP Privacy Key should use a user password as value."
  SYNTAX    INTEGER
        {
            undefined(0),
            userPassword(1),
            userSpecified(2)
        }

FspR7PrivLevel ::= TEXTUAL-CONVENTION
  STATUS        current
  DESCRIPTION
        "User privilege determines the changes a user is allowed to perform."
  SYNTAX    INTEGER
        {
            undefined(0),
            snmpOnly(1),
            crypto(2),
            monitor(3),
            operator(4),
            provision(5),
            admin(6)
        }

FspR7ProtectionRole ::= TEXTUAL-CONVENTION
  STATUS        current
  DESCRIPTION
        "Path label Working or Protect"
  SYNTAX    INTEGER
        {
            undefined(0),
            wkg(1),
            protn(2),
            na(3)
        }

FspR7ProtectionState ::= TEXTUAL-CONVENTION
  STATUS        current
  DESCRIPTION
        "Protection state"
  SYNTAX    INTEGER
        {
            undefined(0),
            noRequest(10),
            doNotRevert(11),
            reversedRequest(12),
            exercise(13),
            waitToRestore(14),
            manualSwitchToWorking(15),
            manualSwitchToProtect(16),
            signalDegradeWorking(17),
            signalDegradeProtect(18),
            signalFailWorking(19),
            forceSwitchToProtect(20),
            forceSwitchToWorking(21),
            signalFailProtect(22),
            lockout(23)
        }

FspR7ProtectionType ::= TEXTUAL-CONVENTION
  STATUS        current
  DESCRIPTION
        ""
  SYNTAX    INTEGER
        {
            undefined(0),
            dpring(1),
            line(2)
        }

FspR7ProtectionTypeCaps ::= TEXTUAL-CONVENTION
  STATUS        current
  DESCRIPTION
        ""
  SYNTAX    BITS
        {
            capUndefined(0),
            capDpring(1),
            capLine(2)
        }

FspR7Protocol ::= TEXTUAL-CONVENTION
  STATUS        current
  DESCRIPTION
        "The Type of the IP Route."
  SYNTAX    INTEGER
        {
            undefined(0),
            local(1), --OS controlled Route
            static(2), --Static Route, Part of database.
            ospf(3) --OSFP controlled Route
        }

FspR7PsuOutputPower ::= TEXTUAL-CONVENTION
  STATUS        current
  DESCRIPTION
        "Maximum PSU Output Power"
  SYNTAX    INTEGER
        {
            undefined(0),
            pwrOut120w(1),
            pwrOut130w(2),
            pwrOut400w(3),
            pwrOut600w(4), --used for high power PSU
            pwrOut170w(5), --used for high power SH1HU-HP/2DC
            pwrOut200w(6), --used for high power SH1HU-HP/2DC
            pwrOut1000w(7), --used forSH9HU
            pwrOut0w(8), --Auxilary value for shelf without integrated power supply unit
            pwrOut800w(9), --used for PSU/7HU-xx-800
            pwrOut150w(10),
            pwrOut1200w(11),
            pwrOut1410w(12),
            pwrOut1450w(13),
            pwrOut2400w(14),
            pwrOut3600w(15),
            pwrOut480w(16),
            pwrOut900w(17), --to support SH3
            pwrOut1100w(18), --to support SH1R and SH1R-2
            pwrOut920w(20), --Used in SH3 for PSM-DC7 and AC7
            pwrOut240w(21) --used for PSU1HU-F-DC
        }

FspR7PsuOutputPowerCaps ::= TEXTUAL-CONVENTION
  STATUS        current
  DESCRIPTION
        "Maximum PSU Output Power"
  SYNTAX    BITS
        {
            capUndefined(0),
            capPwrOut120w(1),
            capPwrOut130w(2),
            capPwrOut400w(3),
            capPwrOut600w(4),
            capPwrOut170w(5),
            capPwrOut200w(6),
            capPwrOut1000w(7),
            capPwrOut0w(8),
            capPwrOut800w(9),
            capPwrOut150w(10),
            capPwrOut1200w(11),
            capPwrOut1410w(12),
            capPwrOut1450w(13),
            capPwrOut2400w(14),
            capPwrOut3600w(15),
            capPwrOut480w(16),
            capPwrOut900w(17),
            capPwrOut1100w(18),
            capPwrOut920w(20),
            capPwrOut240w(21)
        }

FspR7RemoteAuth ::= TEXTUAL-CONVENTION
  STATUS        current
  DESCRIPTION
        "Type of Remote authentication"
  SYNTAX    INTEGER
        {
            undefined(0),
            none(1),
            radius(2),
            tacacs(3)
        }

FspR7RemoteAuthProtocol ::= TEXTUAL-CONVENTION
  STATUS        current
  DESCRIPTION
        "Sets the Authentication Protocol for the Remote Authentication mechanism"
  SYNTAX    INTEGER
        {
            undefined(0),
            pap(1),
            chap(2)
        }

FspR7RenewMode ::= TEXTUAL-CONVENTION
  STATUS        current
  DESCRIPTION
        "Defines SSL certificate renew mode. In AUTOMATIC mode SSL certificate is verified and generated (if needed) at every system startup. In MANUAL mode the user is responsible for generation new SSL certificate when needed."
  SYNTAX    INTEGER
        {
            undefined(0),
            automatic(1),
            manual(2),
            none(3)
        }

FspR7RenewModeCaps ::= TEXTUAL-CONVENTION
  STATUS        current
  DESCRIPTION
        "Defines SSL certificate renew mode. In AUTOMATIC mode SSL certificate is verified and generated (if needed) at every system startup. In MANUAL mode the user is responsible for generation new SSL certificate when needed."
  SYNTAX    BITS
        {
            capUndefined(0),
            capAutomatic(1),
            capManual(2),
            capNone(3)
        }

FspR7RequestAction ::= TEXTUAL-CONVENTION
  STATUS        current
  DESCRIPTION
        "Privilege request action."
  SYNTAX    INTEGER
        {
            undefined(0),
            none(1),
            approve(2),
            deny(3),
            cancel(4)
        }

FspR7RequestErrorType ::= TEXTUAL-CONVENTION
  STATUS        current
  DESCRIPTION
        "Generic error code for snmpset request.
        
        error(3): General error occured
        entityUas(5): Entity in unassigned state
        addressNotExists(6): No such entity exists
        entityAlreadyAssigned(7): Entity already assigned
        entityWrongState(8): Entity cannot be modified due to wrong state
        supportedEntWrongState(12): Entity cannot be modified because supported entity is in wrong state
        supportingEntWrongState(13): Entity cannot be modified because supporting entity is in wrong state
        missingParams(16): Request failed because some parameters are missing
        invalidParams(17): Request failed because some parameters are invalid
        wrongValue(25): Request failed because some parameters has wrong value"
  SYNTAX    INTEGER
        {
            undefined(0),
            error(3),
            entityUas(5),
            addressNotExists(6),
            entityAlreadyAssigned(7),
            entityWrongState(8),
            supportedEntWrongState(12),
            supportingEntWrongState(13),
            missingParams(16),
            invalidParams(17),
            wrongValue(25)
        }

FspR7RequestErrorTypeAes ::= TEXTUAL-CONVENTION
  STATUS        current
  DESCRIPTION
        "Specific error code for Encryption Module.
        
        validPass(1): Valid password. This value will not be shown as this TC is used only for error status
        invalidPass(2): Invalid password
        passRejected(3): Password rejected; After 3 times incorrect password a new set command will be accepted only after timeout
        passNotInit(4): Password not initialized
        passTooSimple(5): Password is too simple and not valid; In case of the new value for the password does not conform security rules checked by the module
        passExpired(6): Password validation aborted because of invalid/expired authentication message counter
        unknown(100): Specific error code unknown"
  SYNTAX    INTEGER
        {
            undefined(0),
            validPass(1), --Valid password
            invalidPass(2), --Invalid crypto officer password provided
            passRejected(3), --Password rejected; After 3 times incorrect password a new set command will be accepted only after timeout
            passNotInit(4), --Password not initialized
            passValFailed(5), --Password is too simple and not valid; In case of the new value for the password does not conform security rules checked by the module
            passExpired(6), --Password validation aborted because of invalid/expired authentication message counter
            passTryAgain(7), --Password validation not possible at the moment - try again later
            notApplicable(100) --Specific error code is not applicable
        }

FspR7RequestState ::= TEXTUAL-CONVENTION
  STATUS        current
  DESCRIPTION
        "Privilege request state."
  SYNTAX    INTEGER
        {
            undefined(0),
            requestSent(1),
            requestCanceled(2),
            requestApproved(3),
            requestDenied(4),
            requestTimeout(5),
            accessExpired(6),
            accessCanceled(7)
        }

FspR7RlsAction ::= TEXTUAL-CONVENTION
  STATUS        current
  DESCRIPTION
        "Rls/Action variable."
  SYNTAX    INTEGER
        {
            undefined(0),
            rls(1),
            action(2)
        }

FspR7RlsActionCaps ::= TEXTUAL-CONVENTION
  STATUS        current
  DESCRIPTION
        "Rls/Action variable."
  SYNTAX    BITS
        {
            capUndefined(0),
            capRls(1),
            capAction(2)
        }

FspR7RoadmNumber ::= TEXTUAL-CONVENTION
  STATUS        current
  DESCRIPTION
        "Number for ROADM module typically associated with a Network Fiber or Degree"
  SYNTAX    INTEGER
        {
            undefined(0),
            rNo1(1),
            rNo2(2),
            rNo3(3),
            rNo4(4),
            rNo5(5),
            rNo6(6),
            rNo7(7),
            rNo8(8),
            rNo9(9),
            rNo10(10),
            rNoNone(11),
            rNo1AND2(12),
            rNo11(13),
            rNo12(14),
            rNo13(15),
            rNo14(16),
            rNo15(17),
            rNo16(18),
            rNo17(19),
            rNo18(20),
            rNo19(21),
            rNo20(22),
            rNo21(23),
            rNo22(24),
            rNo23(25),
            rNo24(26),
            rNo25(27),
            rNo26(28),
            rNo27(29),
            rNo28(30),
            rNo29(31),
            rNo30(32),
            rNo31(33),
            rNo32(34),
            rNo33(35),
            rNo34(36),
            rNo35(37),
            rNo36(38),
            rNo37(39),
            rNo38(40),
            rNo39(41),
            rNo40(42)
        }

FspR7RoadmNumberCaps ::= TEXTUAL-CONVENTION
  STATUS        current
  DESCRIPTION
        "Number for ROADM module typically associated with a Network Fiber or Degree"
  SYNTAX    BITS
        {
            capUndefined(0),
            capRNo1(1),
            capRNo2(2),
            capRNo3(3),
            capRNo4(4),
            capRNo5(5),
            capRNo6(6),
            capRNo7(7),
            capRNo8(8),
            capRNo9(9),
            capRNo10(10),
            capRNoNone(11),
            capRNo1AND2(12),
            capRNo11(13),
            capRNo12(14),
            capRNo13(15),
            capRNo14(16),
            capRNo15(17),
            capRNo16(18),
            capRNo17(19),
            capRNo18(20),
            capRNo19(21),
            capRNo20(22),
            capRNo21(23),
            capRNo22(24),
            capRNo23(25),
            capRNo24(26),
            capRNo25(27),
            capRNo26(28),
            capRNo27(29),
            capRNo28(30),
            capRNo29(31),
            capRNo30(32),
            capRNo31(33),
            capRNo32(34),
            capRNo33(35),
            capRNo34(36),
            capRNo35(37),
            capRNo36(38),
            capRNo37(39),
            capRNo38(40),
            capRNo39(41),
            capRNo40(42)
        }

FspR7RowStatus ::= TEXTUAL-CONVENTION
  STATUS        current
  DESCRIPTION
        "RowStatus"
  SYNTAX    INTEGER
        {
            undefined(0),
            active(1),
            notInService(2),
            notReady(3),
            createAndGo(4),
            createAndWait(5),
            destroy(6)
        }

FspR7RowStatusCaps ::= TEXTUAL-CONVENTION
  STATUS        current
  DESCRIPTION
        "RowStatus"
  SYNTAX    BITS
        {
            capUndefined(0),
            capActive(1),
            capNotInService(2),
            capNotReady(3),
            capCreateAndGo(4),
            capCreateAndWait(5),
            capDestroy(6)
        }

FspR7RPFilter ::= TEXTUAL-CONVENTION
  STATUS        current
  DESCRIPTION
        "Enable/disable Reverse Path Filtering"
  SYNTAX    INTEGER
        {
            undefined(0),
            disable(1),
            strict(2)
        }

FspR7ScepStatus ::= TEXTUAL-CONVENTION
  STATUS        current
  DESCRIPTION
        "SCEP service status - possible values"
  SYNTAX    INTEGER
        {
            undefined(0),
            none(1),
            okay(2),
            requestPending(3),
            networkError(4),
            urlError(5),
            unknownHost(6),
            timeoutError(7),
            protocolError(9), --SCEP protocol error; possibly SCEP service URL is invalid.
            timestampError(10), --SCEP request timestamp error; possibly date/time settings need to be aligned.
            requestError(11), --SCEP request attribute error; possibly CSR contains invalid attributes, esp. request challenge password.
            capabilityError(12), --SCEP server capabilities error, because of missing or unsupported digest/cipher algorithm or request method; possibly can be overriden.
            authorizationError(13), --SCEP server (HTTP) authorization error; possibly NTLM credentials are invalid.
            generalFail(14), --SCEP communication error; generic (unexpected) error.
            certError(16), --SCEP certificate(s) error, because it is either missing or is not a valid certificate.
            certAttributeInvalid(17), --Failed to verify SCEP certificate(s), because of missing or invalid certificate extension(s), esp. keyUsage.
            httpsCertError(18), --UNUSED. HTTPS server certificate(s) error; possibly issuing CA certificate(s) is not known or not trusted.
            certIssuerNotKnown(19), --SCEP certificate(s) error, because issuer is not known; some missing CA certificate needs to be installed.
            certIssuerNotTrusted(20) --SCEP certificate(s) error, because of issuer is not trusted; some installed CA certificate needs to be trusted.
        }

FspR7ScepStatusCaps ::= TEXTUAL-CONVENTION
  STATUS        current
  DESCRIPTION
        "SCEP service status - possible values"
  SYNTAX    BITS
        {
            capUndefined(0),
            capNone(1),
            capOkay(2),
            capRequestPending(3),
            capNetworkError(4),
            capUrlError(5),
            capUnknownHost(6),
            capTimeoutError(7),
            capProtocolError(9),
            capTimestampError(10),
            capRequestError(11),
            capCapabilityError(12),
            capAuthorizationError(13),
            capGeneralFail(14),
            capCertError(16),
            capCertAttributeInvalid(17),
            capHttpsCertError(18),
            capCertIssuerNotKnown(19),
            capCertIssuerNotTrusted(20)
        }

FspR7SdnInterface ::= TEXTUAL-CONVENTION
  STATUS        current
  DESCRIPTION
        "NETCONF and RESTCONF interfaces control."
  SYNTAX    INTEGER
        {
            undefined(0),
            none(1),
            restconf(2),
            netconf(3)
        }

FspR7SdpType ::= TEXTUAL-CONVENTION
  STATUS        current
  DESCRIPTION
        "Determines the amount of Support Data information collected"
  SYNTAX    INTEGER
        {
            undefined(0),
            standard(1),
            compact(2)
        }

FspR7SelfTestFailBehavior ::= TEXTUAL-CONVENTION
  STATUS        current
  DESCRIPTION
        "NCU behavior on selftest failure"
  SYNTAX    INTEGER
        {
            undefined(0),
            nonOperational(1),
            operational(2)
        }

FspR7SessionStatus ::= TEXTUAL-CONVENTION
  STATUS        current
  DESCRIPTION
        "Disable/Enable variable."
  SYNTAX    INTEGER
        {
            undefined(0),
            active(1),
            inactive(2)
        }

FspR7SignalDirection ::= TEXTUAL-CONVENTION
  STATUS        current
  DESCRIPTION
        "Signal Direction"
  SYNTAX    INTEGER
        {
            undefined(0),
            networkToClient(1),
            cientToNetwork(2),
            upgradeToNetwork(3),
            networkToUpgrade(4),
            networkToRoadmAndClient(5),
            roadmAndClientToNetwork(6)
        }

FspR7SingleFiberLocation ::= TEXTUAL-CONVENTION
  STATUS        current
  DESCRIPTION
        "determines the location (A or B) for Single Fiber applications"
  SYNTAX    INTEGER
        {
            undefined(0),
            locationA(1), --location A for SF applications
            locationB(2) --location B for SF applications
        }

FspR7SingleFiberLocationCaps ::= TEXTUAL-CONVENTION
  STATUS        current
  DESCRIPTION
        "determines the location (A or B) for Single Fiber applications"
  SYNTAX    BITS
        {
            capUndefined(0),
            capLocationA(1),
            capLocationB(2)
        }

FspR7SnmpHexString ::= TEXTUAL-CONVENTION
  STATUS        current
  DESCRIPTION
        "An octet string containing Hex values and presenting them in Hex format.
        This textual convention should be used when SnmpAdminString or DisplayString cannot be used,
        because of DISPLAY-HINT limitations."
  SYNTAX    OCTET STRING (SIZE(0..255))

FspR7SnmpLongString ::= TEXTUAL-CONVENTION
  STATUS        current
  DESCRIPTION
        "This textual convention should be used when SnmpAdminString or DisplayString
        cannot be used because of the length limitations."
  SYNTAX    OCTET STRING (SIZE(0..65535))

FspR7SnmpPrivLevel ::= TEXTUAL-CONVENTION
  STATUS        current
  DESCRIPTION
        ""
  SYNTAX    INTEGER
        {
            undefined(0),
            admin(1),
            provision(2),
            operator(3),
            monitor(4),
            crypto(5),
            snmponly(6)
        }

FspR7SnmpSecuLevel ::= TEXTUAL-CONVENTION
  STATUS        current
  DESCRIPTION
        ""
  SYNTAX    INTEGER
        {
            undefined(0),
            noAuthNoPriv(1),
            authNoPriv(2),
            authPriv(3)
        }

FspR7SnmpVersion ::= TEXTUAL-CONVENTION
  STATUS        current
  DESCRIPTION
        "The version of SNMP"
  SYNTAX    INTEGER
        {
            undefined(0),
            ver1(1),
            ver2(2),
            ver3(3)
        }

FspR7SshHostKeyEncryptAlgorithm ::= TEXTUAL-CONVENTION
  STATUS        current
  DESCRIPTION
        "ssh host key encryption alogrithm"
  SYNTAX    INTEGER
        {
            undefined(0),
            rsa(1),
            dsa(2),
            rsa1(3),
            ecdsa(4),
            ed25519(5)
        }

FspR7SshHostKeyLength ::= TEXTUAL-CONVENTION
  STATUS        current
  DESCRIPTION
        "Generated SSH host key length"
  SYNTAX    INTEGER
        {
            undefined(0),
            none(1),
            length256(2), --Relevant for ED25519,ECDSA
            length384(3), --Relevant for ECDSA only
            length521(4), --Relevant for ECDSA only
            length2048(5),
            length3072(6),
            length4096(7)
        }

FspR7Stages ::= TEXTUAL-CONVENTION
  STATUS        current
  DESCRIPTION
        "Number of Stages"
  SYNTAX    INTEGER
        {
            undefined(0),
            st1(1),
            st2(2)
        }

FspR7StateConnection ::= TEXTUAL-CONVENTION
  STATUS        current
  DESCRIPTION
        "State of the Physical Connection"
  SYNTAX    INTEGER
        {
            undefined(0),
            standard(1),
            mismatchEquipment(2),
            mismatchConnection(3),
            mismatchChannel(4),
            mismatchPhysical(5),
            invalidConfig(6),
            nonStandard(7),
            standardSpeq(8),
            partialGroup(9)
        }

FspR7SupplyType ::= TEXTUAL-CONVENTION
  STATUS        current
  DESCRIPTION
        "The kind of power supply - provisioned value"
  SYNTAX    INTEGER
        {
            undefined(0),
            front(1),
            rear(2)
        }

FspR7SupplyTypeCaps ::= TEXTUAL-CONVENTION
  STATUS        current
  DESCRIPTION
        "The kind of power supply - provisioned value"
  SYNTAX    BITS
        {
            capUndefined(0),
            capFront(1),
            capRear(2)
        }

FspR7SwInstallSignAlgorithm ::= TEXTUAL-CONVENTION
  STATUS        current
  DESCRIPTION
        "SW Install digest algorithm to be used for software signing."
  SYNTAX    INTEGER
        {
            undefined(0),
            sha256(5),
            sha384(6),
            sha512(7),
            default(9), --Default (e.g. automatic/negotiated) value, any supported algorithm; actual interpretation and usage depends on application/context.
            defaultSecure(10) --Default (e.g. automatic/negotiated) value, but only algorithms defined as secure/preferred; its interpretation and usage depends on application/context.
        }

FspR7SwitchOverCause ::= TEXTUAL-CONVENTION
  STATUS        current
  DESCRIPTION
        "Cause of Fail-Over or Switch-Over to Partner Controller"
  SYNTAX    INTEGER
        {
            undefined(0),
            notApplicable(1),
            removed(2),
            softwareException(3),
            noResponse(4),
            gracefulShutdown(9),
            switchToDuplex(10),
            buttonPushed(11),
            hbt(5),
            wdog(6),
            hwe(7),
            mld(8),
            ioErr(12)
        }

FspR7SwitchOverCauseCaps ::= TEXTUAL-CONVENTION
  STATUS        current
  DESCRIPTION
        "Cause of Fail-Over or Switch-Over to Partner Controller"
  SYNTAX    BITS
        {
            capUndefined(0),
            capNotApplicable(1),
            capRemoved(2),
            capSoftwareException(3),
            capNoResponse(4),
            capGracefulShutdown(9),
            capSwitchToDuplex(10),
            capButtonPushed(11),
            capHbt(5),
            capWdog(6),
            capHwe(7),
            capMld(8),
            capIoErr(12)
        }

FspR7SwitchMode ::= TEXTUAL-CONVENTION
  STATUS        current
  DESCRIPTION
        "Determines module operation for protection switch operation, OPPM or vSM"
  SYNTAX    INTEGER
        {
            undefined(0),
            oppm(1), --OPPM mode; no VSM functionality
            vsm(2) --VSM functionality
        }

FspR7SwitchModeCaps ::= TEXTUAL-CONVENTION
  STATUS        current
  DESCRIPTION
        "Determines module operation for protection switch operation, OPPM or vSM"
  SYNTAX    BITS
        {
            capUndefined(0),
            capOppm(1),
            capVsm(2)
        }

FspR7SyslogFramingType ::= TEXTUAL-CONVENTION
  STATUS        current
  DESCRIPTION
        "Message Framing Type"
  SYNTAX    INTEGER
        {
            undefined(0),
            nonTransparent(1),
            octetCounting(2)
        }

FspR7SyslogState ::= TEXTUAL-CONVENTION
  STATUS        current
  DESCRIPTION
        "State"
  SYNTAX    INTEGER
        {
            undefined(0),
            initial(1),
            disconnected(2),
            connected(3)
        }

FspR7SyslogTransportProtocol ::= TEXTUAL-CONVENTION
  STATUS        current
  DESCRIPTION
        "Transport Protocol"
  SYNTAX    INTEGER
        {
            undefined(0),
            udp(1),
            tls(2)
        }

FspR7TcmRxMode ::= TEXTUAL-CONVENTION
  STATUS        current
  DESCRIPTION
        "TCM_A Mode Rx"
  SYNTAX    INTEGER
        {
            undefined(0),
            transparent(1),
            operational(2),
            monitor(3)
        }

FspR7TcmRxModeCaps ::= TEXTUAL-CONVENTION
  STATUS        current
  DESCRIPTION
        "TCM_A Mode Rx"
  SYNTAX    BITS
        {
            capUndefined(0),
            capTransparent(1),
            capOperational(2),
            capMonitor(3)
        }

FspR7TcmTxMode ::= TEXTUAL-CONVENTION
  STATUS        current
  DESCRIPTION
        "TCM_A Mode Tx"
  SYNTAX    INTEGER
        {
            undefined(0),
            transparent(1),
            operational(2)
        }

FspR7TcmTxModeCaps ::= TEXTUAL-CONVENTION
  STATUS        current
  DESCRIPTION
        "TCM_A Mode Tx"
  SYNTAX    BITS
        {
            capUndefined(0),
            capTransparent(1),
            capOperational(2)
        }

FspR7TelemetryOutput ::= TEXTUAL-CONVENTION
  STATUS        current
  DESCRIPTION
        "Telemetry interface output provision"
  SYNTAX    INTEGER
        {
            undefined(0),
            neAlmCr(1), --Network Element alarm with critical severity
            neAlmMj(2), --Network Element alarm with major severity
            neAlmMn(3), --Network Element alarm with minor severity
            neAlmMjGe(4), --Network Element alarm with major or greater severity
            neAlmMnGe(5), --Network Element alarm with minor or greater severity
            fcuAlmCr(6), --FCU alarm with critical severity
            fcuAlmMj(7), --FCU alarm with major severity
            fcuAlmMn(8), --FCU alarm with minor severity
            fcuAlmMjGe(9), --FCU alarm with major or greater severity
            fcuAlmMnGe(10), --FCU alarm with minor or greater severity
            psuAlmCr(11), --PSU alarm with critical severity
            psuAlmMj(12), --PSU alarm with major severity
            psuAlmMn(13), --PSU alarm with minor severity
            psuAlmMjGe(14), --PSU alarm with major or greater severity
            psuAlmMnGe(15), --PSU alarm with minor or greater severity
            none(16) --No alarm group assigned
        }

FspR7TelemetryOutputCaps ::= TEXTUAL-CONVENTION
  STATUS        current
  DESCRIPTION
        "Telemetry interface output provision"
  SYNTAX    BITS
        {
            capUndefined(0),
            capNeAlmCr(1),
            capNeAlmMj(2),
            capNeAlmMn(3),
            capNeAlmMjGe(4),
            capNeAlmMnGe(5),
            capFcuAlmCr(6),
            capFcuAlmMj(7),
            capFcuAlmMn(8),
            capFcuAlmMjGe(9),
            capFcuAlmMnGe(10),
            capPsuAlmCr(11),
            capPsuAlmMj(12),
            capPsuAlmMn(13),
            capPsuAlmMjGe(14),
            capPsuAlmMnGe(15),
            capNone(16)
        }

FspR7TerminateSessions ::= TEXTUAL-CONVENTION
  STATUS        current
  DESCRIPTION
        "Shows forced logout availability for selected user and allows to take such an action."
  SYNTAX    INTEGER
        {
            undefined(0),
            allowed(1),
            forbidden(2),
            apply(3)
        }

FspR7TerminationMode ::= TEXTUAL-CONVENTION
  STATUS        current
  DESCRIPTION
        "FSP 3000 C Signal Termination Modes
        Monitor or Terminate 	describes general signal handling at layer
        Mux		indicates if signal is multiplexed or demultiplexed at layer
        Connect		indicates support for Sub Network Connection (SNC), cross-connect"
  SYNTAX    INTEGER
        {
            undefined(0),
            nss(1), --Non-intrusive monitor, same orientation client containment, capable of supporting SNC connections
            trs(2), --Terminated, reverse orientation client containment, capable of supporting SNC connections
            nsn(3), --Non-intrusive monitor, same orientation client containment, SNC not supported
            tsn(4), --Terminated and mapped, same orientation client containment, SNC not supported
            nmss(5), --Non-intrusive monitor, multiplexed, same orientation client containment, capable of supporting SNC connections
            tmsn(6) --Terminated, multiplexed, same orientation client containment, SNC not supported
        }

FspR7TerminationModeCaps ::= TEXTUAL-CONVENTION
  STATUS        current
  DESCRIPTION
        "FSP 3000 C Signal Termination Modes
        Monitor or Terminate 	describes general signal handling at layer
        Mux		indicates if signal is multiplexed or demultiplexed at layer
        Connect		indicates support for Sub Network Connection (SNC), cross-connect"
  SYNTAX    BITS
        {
            capUndefined(0),
            capNss(1),
            capTrs(2),
            capNsn(3),
            capTsn(4),
            capNmss(5),
            capTmsn(6)
        }

FspR7ThProfileParameterTypes ::= TEXTUAL-CONVENTION
  STATUS        current
  DESCRIPTION
        "List of TH profile parameters"
  SYNTAX        INTEGER
                {
                  undefined(0),
               oprHigh(1),
               oprLow(2),
               optHigh(3),
               optLow(4),
               stateOfPolarizationHighThres(5),
               eSOtuHT15min(6),
               eSOtuHT1day(7),
               sESOtuHT15min(8),
               sESOtuHT1day(9),
               uASOtuHT15min(10),
               uASOtuHT1day(11),
               bBEOtuHT15min(12),
               bBEOtuHT1day(13),
               cEFecHT15min(14),
               cEFecHT1day(15),
               uBEFecHT15min(16),
               uBEFecHT1day(17),
               eSFecHT15min(18),
               eSFecHT1day(19),
               sESFecHT15min(20),
               sESFecHT1day(21),
               bERCEFecHT15min(22),
               bERCEFecHT1day(23),
               cRCFrEgrsHT15min(24),
               cRCFrEgrsHT1day(25),
               cRCFrRcvHT15min(26),
               cRCFrRcvHT1day(27),
               eSLHT15min(28),
               eSLHT1day(29),
               sESLHT15min(30),
               sESLHT1day(31),
               uASLHT15min(32),
               uASLHT1day(33),
               bBELHT15min(34),
               bBELHT1day(35),
               cVLHT15min(36),
               cVLHT1day(37),
               eSOduHT15min(38),
               eSOduHT1day(39),
               sESOduHT15min(40),
               sESOduHT1day(41),
               uASOduHT15min(42),
               uASOduHT1day(43),
               bBEOduHT15min(44),
               bBEOduHT1day(45),
               eSPcsHT15min(46),
               eSPcsHT1day(47),
               cVPcsHT15min(48),
               cVPcsHT1day(49),
               sEPcsHT15min(50),
               sEPcsHT1day(51),
               dEPcsHT15min(52),
               dEPcsHT1day(53),
               cVDEPcsHT15min(54),
               cVDEPcsHT1day(55),
               bBEPcsHT15min(56),
               bBEPcsHT1day(57),
               eSSHT15min(58),
               eSSHT1day(59),
               sESSHT15min(60),
               sESSHT1day(61),
               sEFSSHT15min(62),
               sEFSSHT1day(63),
               cVSHT15min(64),
               cVSHT1day(65),
               bBESHT15min(66),
               bBESHT1day(67),
               oOFSSHT15min(68),
               oOFSSHT1day(69),
               eSTcmaHT15min(70),
               eSTcmaHT1day(71),
               sESTcmaHT15min(72),
               sESTcmaHT1day(73),
               uASTcmaHT15min(74),
               uASTcmaHT1day(75),
               bBETcmaHT15min(76),
               bBETcmaHT1day(77),
               eSTcmbHT15min(78),
               eSTcmbHT1day(79),
               sESTcmbHT15min(80),
               sESTcmbHT1day(81),
               uASTcmbHT15min(82),
               uASTcmbHT1day(83),
               bBETcmbHT15min(84),
               bBETcmbHT1day(85),
               eSTcmcHT15min(86),
               eSTcmcHT1day(87),
               sESTcmcHT15min(88),
               sESTcmcHT1day(89),
               uASTcmcHT15min(90),
               uASTcmcHT1day(91),
               bBETcmcHT15min(92),
               bBETcmcHT1day(93),
               logicalLanesSkewHigh(94),
               roundTripDelayLowThres(95),
               roundTripDelayHighThres(96),
               attTxLow(97),
               attTxHigh(98),
               differentialGroupDelayHigh(99),
               qualityFactorLowThres(100),
               oscPwrRcvHighThres(101),
               oscPwrRcvLowThres(102),
               carrierFreqOffsetHigh(103),
               carrierFreqOffsetLow(104),
               latencyHighThres(105),
               latencyLowThres(106),
               attRcvLow(107),
               attRcvHigh(108),
               brPwrReceivedHighThres(109),
               chromaticDispersionHigh(110),
               chromaticDispersionLow(111),
               dispersionCompensationLowThres(112),
               dispersionCompensationHighThres(113),
               signalToNoiseRatioLow(114)
                }

FspR7ThrCategory ::= TEXTUAL-CONVENTION
  STATUS        current
  DESCRIPTION
        "Threshold Category"
  SYNTAX    INTEGER
        {
            undefined(0),
            thrcNone(1),
            thrcSopt(2),
            thrcOtu(3),
            thrcFec(4),
            thrcEthTx(5),
            thrcEthRx(6),
            thrcSonetL(7),
            thrcOdu(8),
            thrcPcs(9),
            thrcSonetS(10),
            thrcTcma(11),
            thrcTcmb(12),
            thrcTcmc(13),
            thrcSkew(14),
            thrcRndtrpdly(15),
            thrcAttrmt(16),
            thrcDgd(17),
            thrcQfact(18),
            thrcOscpwr(19),
            thrcCfot(20),
            thrcLatency(21),
            thrcAtrcv(22),
            thrcBr(23),
            thrcCd(24),
            thrcCdc(25),
            thrcSnr(26),
            thrcXfpC(100),
            thrcXfpD(101),
            thrcXfptD(102),
            thrcXfpOtnD(103),
            thrcXfptlnD(104),
            thrcXfpG(105),
            thrcXfpBG(106),
            thrcSfpC(107),
            thrcSfpD(108),
            thrcSfpG(109),
            thrcSfpGHd(239),
            thrcSfpBC(110),
            thrcSfpBG(111),
            thrcSfpBCdrG(112),
            thrcSfptD(113),
            thrc4CfptD(114),
            thrcCfp4g(115),
            thrcCfp10g(116),
            thrcCfptCd(117),
            thrcCfpTfCd(118),
            thrcCfpTgCd(119),
            thrcCfpTrCd(120),
            thrcSfpCdrG(121),
            thrcSfpCdrD(122),
            thrcSfpCdrC(123),
            thrc4cfpd(124),
            thrcSfpTlnD(125),
            thrcSfpRxTxG(126),
            thrcSfp2TxG(127),
            thrcSfp2RxG(128),
            thrcQSfp4g(129),
            thrcQSfp4gHd(130),
            thrc4QsfpG(131),
            thrc4QsfpGHd(132),
            thrcQSfp10g(133),
            thrcQSfp10gHd(134),
            thrcCfp2tCd(135),
            thrcCfp2tCdHd(136),
            thrc4RoadmEC96N(137),
            thrc4RoadmEC96C(138),
            thrcMp2B4ctN(139),
            thrcQSfpAoc(140),
            thrcQSfpAocHd(141),
            thrcCfpTlCd(142),
            thrc4roadmC96N(143),
            thrc4roadmC96C(144),
            thrcTMp2D12CtN(145),
            thrcMp2B4CtSN(146),
            thrcCfp2tgCd(147),
            thrcCfp2tgCdHd(148),
            thrc10tcc100gtbDN(149),
            thrc10tcc10gcN(150),
            thrc10tcc10gdN(151),
            thrc10tcc10gtdN(152),
            thrc10tccs10gtdN(153),
            thrc16PSM4N(154),
            thrc16PSM8N(155),
            thrc2EdfaS20S10U(156),
            thrc2EdfaS20S10N(157),
            thrc2RamanC15U(158),
            thrc2RamanU(159),
            thrc4opcmN(160),
            thrc4tca4gcN(161),
            thrc4tca4gdN(162),
            thrc4tcc10gcN(163),
            thrc4tcc10gdN(164),
            thrc4Tcc10gtdN(165),
            thrc4Tcc40gtdN(166),
            thrc5tce10gtdN(167),
            thrc5tce10gtaesdN(168),
            thrc5tces10gtdN(169),
            thrc5tces10gtaesdN(170),
            thrc8CcmC80C(171),
            thrc8CcmC80N(172),
            thrc8psm8N(173),
            thrc8roadmC40C(174),
            thrc8roadmC40N(175),
            thrc8RoadmC80C(176),
            thrc8RoadmC80N(177),
            thrc8tca10gcN(178),
            thrc8tca10gdN(179),
            thrc96Csm2HuDN(180),
            thrc9ccmC96C(181),
            thrc9ccmC96V(182),
            thrc9ccmC96N(183),
            thrc9RoadmC96C(184),
            thrc9RoadmC96N(185),
            thrc9RoadmRsC(186),
            thrc9RoadmRsV(187),
            thrc9RoadmRsN(188),
            thrcAmpShgcvU(189),
            thrcAmpShgcvN(190),
            thrcAmpSlgcvU(191),
            thrcAmpSlgcvN(192),
            thrcccm8C(193),
            thrcccm8N(194),
            thrcEdfaD27U(195),
            thrcEdfadgcN(196),
            thrcEdfaDgcvN(197),
            thrcEdfasN(198),
            thrcEdfaS20U(199),
            thrcEdfaS20N(200),
            thrcEdfaS26U(201),
            thrcEdfasgcN(202),
            thrcEdfaSgcbN(203),
            thrcEroadmDcU(204),
            thrcEroadmDcN(205),
            thrcMaOscCO(206),
            thrcMaOscCC(207),
            thrcMaOscCN(208),
            thrcMroadmC96P(209),
            thrcMtOscCO(210),
            thrcMtOscCC(211),
            thrcMtOscCP(212),
            thrcMtOscCN(213),
            thrcOppmC(214),
            thrcOppmN(215),
            thrcPsmxMRoadmC(216),
            thrcPsmxMRoadmP(217),
            thrcPsmxMRoadmN(218),
            thrcRamanU(219),
            thrcRoadmC80C(220),
            thrcRoadmC80U(221),
            thrcRoadmC80N(222),
            thrcWca10gcN(223),
            thrcWca10gdN(224),
            thrcWcc100gtDN(225),
            thrcWcc100gtbDN(226),
            thrcWcc10gcN(227),
            thrcWcc10gdN(228),
            thrcWcc10gtdN(229),
            thrcWcc2g7cN(230),
            thrcWcc2g7dN(231),
            thrcWcc40gtdC(232),
            thrcWcc40gtdN(233),
            thrcTMp2D8CtN(234),
            thrcQsfp2bG(235),
            thrcQsfp2bGHd(236),
            thrcCfp2tbCd(237),
            thrcCfp2tbCdHd(238),
            thrcTMp2D3DtN(240),
            thrcSfpGmD(241),
            thrcCfptaCd(242),
            thrcSfpGmCdrD(243),
            thrcQSfp8g(244),
            thrcQSfp8gHd(245),
            thrcQSfp1g(246),
            thrcQSfp1gHd(247),
            thrcSfpcHd(248),
            thrcSfpdHd(249),
            thrcSfptdHd(250),
            thrc16psm4C(251),
            thrc16psm8C(252),
            thrc8psm8C(253),
            thrcTMpM8DCtN(254),
            thrcTMp2D8DCtN(255),
            thrcSfpBGHd(256),
            thrcSfpBCdrGHd(257),
            thrcSfpTlnDHd(258),
            thrcSfpAdtran(259),
            thrcXfpAdtran(260),
            thrcSfpOdC(261),
            thrcSfpOdG(262),
            thrcSfpNonApprovedHd(263),
            thrcQSfpNonApprovedHd(264),
            thrcSfpAdtranHd(265),
            thrcSfpNonApproved(266),
            thrcQSfpNonApproved(267),
            thrcMp2B4CtCgN(268),
            thrcCfp2tBCd(269),
            thrcCfp2tBCdHd(270),
            thrcSfptAD(271)
        }

FspR7ThrFamily ::= TEXTUAL-CONVENTION
  STATUS        current
  DESCRIPTION
        "Threshold Family"
  SYNTAX    INTEGER
        {
            undefined(0),
            physicalLayer(1),
            dataLayer(2),
            plug(3),
            module(4)
        }

FspR7TiltSet ::= TEXTUAL-CONVENTION
  STATUS        current
  DESCRIPTION
        "Tilt setting as discrete values versus a range"
  SYNTAX    INTEGER
        {
            undefined(0),
            minus1dB0(1),
            minus1dB5(2),
            minus2dB0(3)
        }

FspR7TiltSetCaps ::= TEXTUAL-CONVENTION
  STATUS        current
  DESCRIPTION
        "Tilt setting as discrete values versus a range"
  SYNTAX    BITS
        {
            capUndefined(0),
            capMinus1dB0(1),
            capMinus1dB5(2),
            capMinus2dB0(3)
        }

FspR7TimDetMode ::= TEXTUAL-CONVENTION
  STATUS        current
  DESCRIPTION
        "OTU Trace Identifier Mismatch (TIM) strings compared to generate TIM defect."
  SYNTAX    INTEGER
        {
            undefined(0),
            none(1), --expected TTI strings are not compared to acquired TTI strings. dTIM never generated
            sapiDapi(2), --dTIM generated based on expected SAPI and expected DAPI.
            sapi(3), --dTIM generated based on SAPI substring only
            dapi(4) --dTIM generated based on DAPI substring only.
        }

FspR7TimDetModeCaps ::= TEXTUAL-CONVENTION
  STATUS        current
  DESCRIPTION
        "OTU Trace Identifier Mismatch (TIM) strings compared to generate TIM defect."
  SYNTAX    BITS
        {
            capUndefined(0),
            capNone(1),
            capSapiDapi(2),
            capSapi(3),
            capDapi(4)
        }

FspR7TimeShort ::= TEXTUAL-CONVENTION
  DISPLAY-HINT        "1d-1d"
  STATUS        current
  DESCRIPTION
        "A time specification.
        field  octets  contents  range
        -----  ------  --------  -----
        1      1       hour    0..23
        2      1     minutes   0..59
        For example: 13-10"
  SYNTAX    OCTET STRING (SIZE(2..2))

FspR7TLSSupport ::= TEXTUAL-CONVENTION
  STATUS        current
  DESCRIPTION
        "TLS protocol version support."
  SYNTAX    INTEGER
        {
            undefined(0),
            legacy(1),
            current(2)
        }

FspR7Topology ::= TEXTUAL-CONVENTION
  STATUS        current
  DESCRIPTION
        "Shows the card topology in the NE"
  SYNTAX    INTEGER
        {
            undefined(0),
            standAlone(1 ), --One stand alone card in a shelf
            backToBack(2), --Two cards communicating over the backplane in a shelf
            mesh(3), --Three cards communicating over the backplane in a shelf
            fabric(4) --Many cards communicating via the UxM module
        }

FspR7TopologyCaps ::= TEXTUAL-CONVENTION
  STATUS        current
  DESCRIPTION
        "Shows the card topology in the NE"
  SYNTAX    BITS
        {
            capUndefined(0),
            capStandAlone(1 ),
            capBackToBack(2),
            capMesh(3),
            capFabric(4)
        }

FspR7TopologyType ::= TEXTUAL-CONVENTION
  STATUS        current
  DESCRIPTION
        "Monitored Topology Type"
  SYNTAX    INTEGER
        {
            undefined(0),
            lad(1),
            ring(2),
            p2p(3),
            unknown(4)
        }

FspR7TrafficDirection ::= TEXTUAL-CONVENTION
  STATUS        current
  DESCRIPTION
        "Traffic Direction"
  SYNTAX    INTEGER
        {
            undefined(0),
            bidi(1), --Bidirectional Traffic (standard application)
            uniCton(2),
            uniNtoc(3),
            uniWtoe(4),
            uniEtow(5),
            txcrs(6), --Unidirectional traffic; Naming convention: CRS transmitts data to CH, UCH,VCH or others entities
            rxcrs(7) --Unidirectional traffic; Naming convention:CRS receives data from CH, UCH, VCH or other entities
        }

FspR7TrafficDirectionCaps ::= TEXTUAL-CONVENTION
  STATUS        current
  DESCRIPTION
        "Traffic Direction"
  SYNTAX    BITS
        {
            capUndefined(0),
            capBidi(1),
            capUniCton(2),
            capUniNtoc(3),
            capUniWtoe(4),
            capUniEtow(5),
            capTxcrs(6),
            capRxcrs(7)
        }

FspR7TransferProtocol ::= TEXTUAL-CONVENTION
  STATUS        current
  DESCRIPTION
        "Download Protocol"
  SYNTAX    INTEGER
        {
            undefined(0),
            ftp(1), --File Transfer Protocol
            tftp(2), --Trivial File Transfer Protocol
            scp(3), --Secure CoPy; the entire conversation (credentials and data) is always protected by SSH protocol
            http(4), --File transfer via HTTP protocol
            sftp(5), --Secure File Transfer Protocol; SCP overlay
            scpKeyBased(6), --Secure File Transfer Protocol with Keybased Authetication
            sftpKeyBased(7) --Secure File Transfer Protocol with Keybased Authetication; SCP overlay
        }

FspR7TransmissionMode ::= TEXTUAL-CONVENTION
  STATUS        current
  DESCRIPTION
        "Mode of the module, determine operation or functionality"
  SYNTAX    INTEGER
        {
            undefined(0),
            trans(1), --Simple transport of signal without protection on a TRANSponder card with only one network port for which it is default.
            transE(2), --Simple transport of signal without protection using the port CH-NE.
            transW(3), --Simple transport of signal without protection using the port CH-NW.
            transHst(4), --Transport of signal with network port protection (only on TRANSponder cards with two network ports, for which it is default).
            mux(5), --Simple aggregation of signals without protection on a MUXponder card with only one network port - for which it is default.
            muxE(6), --Simple aggregation of signals without protection using the port CH-NE.
            muxW(7), --Simple aggregation of signals without protection using the port CH-NW.
            muxHst(8), --Aggregation of signals with network port protection (only on MUXponder cards with two network ports - for which it is default).
            regen1Way(9), --Regeneration of signal using network port(s).
            regen2Way(10), --Regeneration of signal using network port(s).
            obsolete(11), --To remove.
            adm(12), --Add, Drop, Passthrough, Drop and Continue Fuctionality
            transDual(13), --Dual Transport of signal without protection on a Transponder card with two network ports
            muxDual(14), --Dual Transport of signal without protection on a Muxponder card with two network ports
            nFixed(15), --Add/Drop channels connected to the associated Network Fiber. Channel filter must be connected to C port associated with the ROADM number 
            cSelect(16), --Add/Drop channels can be connected to any Network Fiber. Channel filter must be connected to N port. C port associated with ROADM number is not connected.
            dualClient(17), --Two (2) client ports are allocated for add/drop.  Add/Drop channels for C-Even wavelengths (1-40) are allocated to C port associated with the ROADM number. Add/Dropchannels for C-Odd wavelengths (41-80) are allocated to C8 port.
            xc(20), --(X)cross Connect mode. Used on cards that cross connects traffic between generic ports.
            transQuad(21), -- Quad Transport of signal without protection on a Transponder card
            transQuintuple(22), --Quintuple Transport of signal without protection on a Transponder card
            std(23), --Traffic Path is between C port and this N Port only
            pair(24), --Traffic Path is between C port and this N Port and N Port designated as the protection partner. Channel protection requries FFP to be added.
            mux10GEnterprise(25), --10G Multiplexer with Enterprise feature set
            colorless(26),
            trans1(27), --Transparent STM-64 -> OTU2, 10GE -> OTU2e, 8GFC -> OTU2F
            trans2(28), --OTU2 client signals
            trans3(29), --Transparent STM-64 -> OTU2, 10GE -> OTU2e, 8G-FC -> OTUf 
            singleCc(31),
            dualCc(32),
            trans6(35) --Sextuple Transport of signal on a Transponder card
        }

FspR7TransmissionModeCaps ::= TEXTUAL-CONVENTION
  STATUS        current
  DESCRIPTION
        "Mode of the module, determine operation or functionality"
  SYNTAX    BITS
        {
            capUndefined(0),
            capTrans(1),
            capTransE(2),
            capTransW(3),
            capTransHst(4),
            capMux(5),
            capMuxE(6),
            capMuxW(7),
            capMuxHst(8),
            capRegen1Way(9),
            capRegen2Way(10),
            capObsolete(11),
            capAdm(12),
            capTransDual(13),
            capMuxDual(14),
            capNFixed(15),
            capCSelect(16),
            capDualClient(17),
            capXc(20),
            capTransQuad(21),
            capTransQuintuple(22),
            capStd(23),
            capPair(24),
            capMux10GEnterprise(25),
            capColorless(26),
            capTrans1(27),
            capTrans2(28),
            capTrans3(29),
            capSingleCc(31),
            capDualCc(32),
            capTrans6(35)
        }

FspR7TrueFalse ::= TEXTUAL-CONVENTION
  STATUS        current
  DESCRIPTION
        "True False variable."
  SYNTAX    INTEGER
        {
            undefined(0),
            true(1),
            false(2)
        }

FspR7TrueFalseCaps ::= TEXTUAL-CONVENTION
  STATUS        current
  DESCRIPTION
        "True False variable."
  SYNTAX    BITS
        {
            capUndefined(0),
            capTrue(1),
            capFalse(2)
        }

FspR7TrunkGroup ::= TEXTUAL-CONVENTION
  STATUS        current
  DESCRIPTION
        "Trunk Group"
  SYNTAX    INTEGER
        {
            undefined(0),
            none(1), --Member of Trunk Group
            group1(2) --Member of Trunk Group1
        }

FspR7TrunkGroupCaps ::= TEXTUAL-CONVENTION
  STATUS        current
  DESCRIPTION
        "Trunk Group"
  SYNTAX    BITS
        {
            capUndefined(0),
            capNone(1),
            capGroup1(2)
        }

FspR7TxOffOnTm ::= TEXTUAL-CONVENTION
  STATUS        current
  DESCRIPTION
        "Relevant only when ERRFWD=TXOFF. Enables/disables the
        possibility to delay turning off and on the the transmitter.
        This applies to the case when turning off the transmitter
        is done  as an error forwarding mechanism."
  SYNTAX    INTEGER
        {
            undefined(0),
            disable(1),
            enableTxOffTm(2),
            enableTxOnTm(3)
        }

FspR7TxOffOnTmCaps ::= TEXTUAL-CONVENTION
  STATUS        current
  DESCRIPTION
        "Relevant only when ERRFWD=TXOFF. Enables/disables the
        possibility to delay turning off and on the the transmitter.
        This applies to the case when turning off the transmitter
        is done  as an error forwarding mechanism."
  SYNTAX    BITS
        {
            capUndefined(0),
            capDisable(1),
            capEnableTxOffTm(2),
            capEnableTxOnTm(3)
        }

FspR7TypeConnection ::= TEXTUAL-CONVENTION
  STATUS        current
  DESCRIPTION
        "Type of equipment connection"
  SYNTAX    INTEGER
        {
            undefined(0),
            connection1Way(1),
            connection2Way(2)
        }

FspR7TypeConnectionCaps ::= TEXTUAL-CONVENTION
  STATUS        current
  DESCRIPTION
        "Type of equipment connection"
  SYNTAX    BITS
        {
            capUndefined(0),
            capConnection1Way(1),
            capConnection2Way(2)
        }

FspR7TypeCrs ::= TEXTUAL-CONVENTION
  STATUS        current
  DESCRIPTION
        "Type of Cross-Connect"
  SYNTAX    INTEGER
        {
            undefined(0),
            connection1Way(1), --Unidirectional CRS
            connection2Way(2), --Bidirectional CRS
            connection1WayProt(3), --Unidirectional CRS with protection
            connection2WayProt(4), --Bidirectional CRS with protection
            connection1WayMc(5), --Unidirectional multicast CRS
            connection1WayDc(6), --Unidirectional Drop and Continue
            connection1WayDcProt(7), --Unidirectional Drop and Continue with protection
            connection1WayMcProt(8), --Unidirectional multicast with protection
            connection1WayCont(9), --Unidirectional Continue Path
            connection2WayCont(10) --Bidirectional Continue Path
        }

FspR7TypeCrsCaps ::= TEXTUAL-CONVENTION
  STATUS        current
  DESCRIPTION
        "Type of Cross-Connect"
  SYNTAX    BITS
        {
            capUndefined(0),
            capConnection1Way(1),
            capConnection2Way(2),
            capConnection1WayProt(3),
            capConnection2WayProt(4),
            capConnection1WayMc(5),
            capConnection1WayDc(6),
            capConnection1WayDcProt(7),
            capConnection1WayMcProt(8),
            capConnection1WayCont(9),
            capConnection2WayCont(10)
        }

FspR7WebSessionResumption ::= TEXTUAL-CONVENTION
  STATUS        current
  DESCRIPTION
        "Configures HTTPS/TLS session resumption mechanism."
  SYNTAX    INTEGER
        {
            undefined(0),
            none(1),
            sessionId(2),
            sessionTicket(3),
            both(4)
        }

FspR7Unsigned32Caps ::= TEXTUAL-CONVENTION
  DISPLAY-HINT        "4d:4d"
  STATUS        current
  DESCRIPTION
        "A FspR7Unsigned32Caps specification.
        1..4 bytes - minValue(Unsigned32),
        5..8 bytes - maxValue(Unsigned32)."
  SYNTAX    OCTET STRING (SIZE(0..8))

FspR7UntaggedFrames ::= TEXTUAL-CONVENTION
  STATUS        current
  DESCRIPTION
        "If untagged frames shall be enabled on this port or not."
  SYNTAX    INTEGER
        {
            undefined(0),
            accept(1),
            reject(2)
        }

FspR7UntaggedFramesCaps ::= TEXTUAL-CONVENTION
  STATUS        current
  DESCRIPTION
        "If untagged frames shall be enabled on this port or not."
  SYNTAX    BITS
        {
            capUndefined(0),
            capAccept(1),
            capReject(2)
        }

FspR7UserInterface ::= TEXTUAL-CONVENTION
  STATUS        current
  DESCRIPTION
        "User Interface currently being used by the user"
  SYNTAX    INTEGER
        {
            undefined(0),
            ned(1),
            craft(2),
            snmp(3)
        }

FspR7ValidityPeriod ::= TEXTUAL-CONVENTION
  STATUS        current
  DESCRIPTION
        "Period of time (in years) a generated SSL certificate is valid."
  SYNTAX    INTEGER
        {
            undefined(0),
            oneYear(1),
            twoYears(2),
            threeYears(3),
            fourYears(4),
            fiveYears(5)
        }

FspR7ValidityPeriodCaps ::= TEXTUAL-CONVENTION
  STATUS        current
  DESCRIPTION
        "Period of time (in years) a generated SSL certificate is valid."
  SYNTAX    BITS
        {
            capUndefined(0),
            capOneYear(1),
            capTwoYears(2),
            capThreeYears(3),
            capFourYears(4),
            capFiveYears(5)
        }

FspR7VoaMode ::= TEXTUAL-CONVENTION
  STATUS        current
  DESCRIPTION
        "VOA operating mode"
  SYNTAX    INTEGER
        {
            undefined(0),
            power(1), --Constant power mode
            att(2) --Constant attenuation mode
        }

FspR7VoaModeCaps ::= TEXTUAL-CONVENTION
  STATUS        current
  DESCRIPTION
        "VOA operating mode"
  SYNTAX    BITS
        {
            capUndefined(0),
            capPower(1),
            capAtt(2)
        }

FspR7VSessChangeReason ::= TEXTUAL-CONVENTION
  STATUS        current
  DESCRIPTION
        "Last operation status"
  SYNTAX    INTEGER
        {
            undefined(0),
            none(1),
            requestIssued(2),
            requestApproved(3),
            requestDenied(4),
            requestTimeout(5),
            accessTimeout(6),
            accessRevoked(7)
        }

FspR7VSessStatus ::= TEXTUAL-CONVENTION
  STATUS        current
  DESCRIPTION
        "Read-only object that describes current status of user session.
        There are 3 possible valid values of this object:
        - Normal(1) - default session status.
        - writeAcsRequested(2) - status assigned to session that requested write access and is waiting for ADMIN response
        After time equal 'write access request timeout' if session status has not been changed it will automatically change back to normal(1) and fspR7WriteAccessRequestTimeout trap will be sent.
        - writeAcsGranted(3) - write access has been granted by ADMIN user. Session can act as if it had PROVISION privilege level.
        After time equal virtualSessionTimeout session status will be automatically changed to normal(1) and fspR7WriteAccessTimeout trap will be sent."
  SYNTAX    INTEGER
        {
            undefined(0),
            normal(1),
            writeAcsRequested(2),
            writeAcsGranted(3)
        }

FspR7VSessWriteAccess ::= TEXTUAL-CONVENTION
  STATUS        current
  DESCRIPTION
        "Read-write parameter used to manipulate write access of the user. SNMPGET/SNMPGETNEXT will always return none(4) value for this parameter. It can be set to multiple values depending of sessionStatus:
        - request(1) - settable only by MONITOR if his sessionStatus is equal normal. Causes change of sessionStatus to writeAcsRequested(2). Trap FspR7WriteAccessRequest will be sent.
        - revoke(2) - settable both by MONITOR user and ADMIN user, only if session status is equal writeAcsRequested(2) or writeAcsGranted(3).
        If session status is equal writeAcsRequested(2) setting this value  will change session status back to normal(1). Depending on author of action fspR7WriteAccessRevoked (MONITOR) or fspR7WriteAccessDenied (ADMIN) trap will be sent.
        If session status is equal writeAcsGranted(3) it will be changed to normal(1).  fspR7WriteAccessRevoked trap will be sent.
        - Grant(3) - settable only by ADMIN user only when session status is equal writeAcsRequested(2). Setting this value will change session staus to writeAcsGranted (3), additionally fspR7WriteAccessGranted trap will be sent."
  SYNTAX    INTEGER
        {
            undefined(0),
            request(1),
            revoke(2),
            grant(3),
            none(4)
        }

FspR7XfpDecisionThres ::= TEXTUAL-CONVENTION
  STATUS        current
  DESCRIPTION
        "XFP Decision threshold setting"
  SYNTAX    INTEGER
        {
            undefined(0),
            standard(1),
            forwardRaman(2)
        }

FspR7XfpDecisionThresCaps ::= TEXTUAL-CONVENTION
  STATUS        current
  DESCRIPTION
        "XFP Decision threshold setting"
  SYNTAX    BITS
        {
            capUndefined(0),
            capStandard(1),
            capForwardRaman(2)
        }

FspR7YcableType ::= TEXTUAL-CONVENTION
  STATUS        current
  DESCRIPTION
        "Type of Y-cable"
  SYNTAX    INTEGER
        {
            undefined(0),
            ycabSmLc(1), --Y-Cable with single mode fiber and LC connector on all ports
            ycabMmLc(2), --Y-Cable with multi mode fiber and LC connector on all ports
            ycabSmScLc(3), --Y-Cable with single mode fiber, SC connector @client Port and LC connector @network port
            ycabMmScLc(4), --Y-Cable with multimode fiber, SC connector @client Port and LC connector @network port
            ycabSmFcLc(5), --Y-Cable with single mode fiber, FC connector @client Port and LC connector @network port
            ycabMm50Lc(6) --Y-Cable with OM3 type multi mode fiber and LC connector on all ports
        }

FspR7YcableTypeCaps ::= TEXTUAL-CONVENTION
  STATUS        current
  DESCRIPTION
        "Type of Y-cable"
  SYNTAX    BITS
        {
            capUndefined(0),
            capYcabSmLc(1),
            capYcabMmLc(2),
            capYcabSmScLc(3),
            capYcabMmScLc(4),
            capYcabSmFcLc(5),
            capYcabMm50Lc(6)
        }

FspR7FltrCableType ::= TEXTUAL-CONVENTION
  STATUS        current
  DESCRIPTION
        "Filter Cable"
  SYNTAX    INTEGER
        {
            undefined(0),
            fltrCabLr4SmLc(1) --LR4 Filter Cable for single mode fiber with LC connectors on all ports
        }

FspR7FltrCableTypeCaps ::= TEXTUAL-CONVENTION
  STATUS        current
  DESCRIPTION
        "Filter Cable"
  SYNTAX    BITS
        {
            capUndefined(0),
            capFltrCabLr4SmLc(1)
        }

FspR7YesNo ::= TEXTUAL-CONVENTION
  STATUS        current
  DESCRIPTION
        "YesNo variable."
  SYNTAX    INTEGER
        {
            undefined(0),
            yes(1),
            no(2)
        }

FspR7YesNoCaps ::= TEXTUAL-CONVENTION
  STATUS        current
  DESCRIPTION
        "YesNo variable."
  SYNTAX    BITS
        {
            capUndefined(0),
            capYes(1),
            capNo(2)
        }

FspR7RlsColdWarm ::= TEXTUAL-CONVENTION
  STATUS        current
  DESCRIPTION
        "Rls/Cold/Warm variable."
  SYNTAX    INTEGER
        {
            undefined(0),
            rls(1),
            cold(2),
            warm(3)
        }

FspR7RlsColdWarmCaps ::= TEXTUAL-CONVENTION
  STATUS        current
  DESCRIPTION
        "Rls/Cold/Warm variable."
  SYNTAX    BITS
        {
            capUndefined(0),
            capRls(1),
            capCold(2),
            capWarm(3)
        }


END
